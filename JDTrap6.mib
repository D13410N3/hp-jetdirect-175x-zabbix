--
--  /****************************************************************/
--  /* (C) COPYRIGHT HEWLETT-PACKARD COMPANY 1996.  ALL RIGHTS      */
--  /* RESERVED.  NO PART OF THIS DOCUMENT MAY BE PHOTOCOPIED,      */
--  /* REPRODUCED OR TRANSLATED WITHOUT THE PRIOR WRITTEN CONSENT   */
--  /* OF HEWLETT-PACKARD COMPANY.                                  */
--  /****************************************************************/
-- This MIB file is the TRAP MIB file for the JetDirect SNMP 
-- implementation.
-- It includes all traps delivered by internal cards and external
-- boxes.
--
-- Last Updated:  29 May 2001

-- HP OBJECT IDENTIFIER ::= { iso org(3) dod(6) internet(1) private(4) enterprises(1) 11 }

JETDIRECT3-TRAP DEFINITIONS ::= BEGIN

IMPORTS
     private, enterprises, Counter, Gauge, TimeTicks, NetworkAddress, mgmt
          FROM RFC1155-SMI;
         
	  -- textual conventions

          DisplayString ::=
              OCTET STRING
          -- This data type is used to model textual information taken
          -- from the NVT ASCII character set.  By convention, objects
          -- with this syntax are declared as having
          --
          --      SIZE (0..255)

hp                  OBJECT IDENTIFIER ::=  { enterprises 11 }
nm                  OBJECT IDENTIFIER ::=  { hp 2 }
system              OBJECT IDENTIFIER ::=  { nm 3 }
netPeripheral       OBJECT IDENTIFIER ::=  { system 9 }
netPrinter          OBJECT IDENTIFIER ::=  { netPeripheral 1 }

	periphStatusChange TRAP-TYPE
		ENTERPRISE	netPrinter
		DESCRIPTION
			"The status of the peripheral has changed"
	::= 1



-- specific OID values are derived from PJL USTATUS Codes
-- The following applies
--		Informational Messages: 		10xxx
--		Background Paper Mount: 		11xyy
--		Background Paper Tray Status: 	12xyy
--		Output Bin Status:				15xxy
--		PJL Parser Errors:				20xxx
--		PJL Parser Warnings:			25xxx
-- 		PJL Semantic Errors:			27xxx
--		Auto-Continuable Conditions:	30xxx
--		PJL File System Errors:			32xxx
--		Possible Operator Invervention
--			Conditions:					35xxx
--		Operator Intervention Required:	40xxx
--		Foreground Paper Mount:			41xyy
--		Paper Jam Errors:				42xyy
--		Optional (External) Paper 
--			Handling Device Messages	43xyy
--		Paper Jam Messages:				44xyy
--		Hardware Errors:				50xxx

-- Object types

-- Informational Messages - Some of these messages are legacy 
-- and are no longer used.  They are included for completness


	periphInfoReady TRAP-TYPE
		ENTERPRISE	netPrinter
		DESCRIPTION
			"The peripheral has been placed online or
			 in the ready state"
	::= 10001

	periphInfoNotReady TRAP-TYPE
		ENTERPRISE	netPrinter
		DESCRIPTION
			"The peripheral has been placed offine or
			 in the not-ready state.  It may still be
			 able to accept jobs, but these jobs may
			 only be buffered and not processed"
	::= 10002

	periphInfoWarmingUp TRAP-TYPE
		ENTERPRISE	netPrinter
		DESCRIPTION
			"The peripheral is coming out of power-save
			 mode"
	::= 10003

	periphInfoSelfTest1 TRAP-TYPE
		ENTERPRISE	netPrinter
		DESCRIPTION
			"The peripheral is performing a self test 
			 or internal test"
	::= 10004


	periphInfoReset TRAP-TYPE
		ENTERPRISE	netPrinter
		DESCRIPTION
			"The peripheral is executing a reset of itself. 
			 A function typically selected from the front 
			 panel menu of the peripheral"
	::= 10005

	periphInfoTonerLow TRAP-TYPE
		ENTERPRISE	netPrinter
		DESCRIPTION
			"The peripheral has detected that its toner 
			 cartridge is running low on toner."
	::= 10006

	periphInfoCancellingJob TRAP-TYPE
		ENTERPRISE	netPrinter
		DESCRIPTION
			"The peripheral is in the process of cancelling
                         a job."
	::= 10007

	periphInfoMioOrEioNotReady TRAP-TYPE
		ENTERPRISE	netPrinter
		DESCRIPTION
			"The peripheral has detected one or more
			 of its MIO/EIO slots has an internal card
			 installed which is not responding or is 
			 reporting to the peripheral it is not ready"
	::= 10011

	periphInfoSelfTest2 TRAP-TYPE
		ENTERPRISE	netPrinter
		DESCRIPTION
			"The peripheral is performing a self test 
			 or internal test"
	::= 10013

	periphInfoPrintingTestPage TRAP-TYPE
		ENTERPRISE	netPrinter
		DESCRIPTION
			"The peripheral is printing a config page
			 or self-test page"
	::= 10014

	periphInfoPrintingFontList TRAP-TYPE
		ENTERPRISE	netPrinter
		DESCRIPTION
			"The peripheral is printing the typeface
			 list or font list"
	::= 10015

	periphInfoEngineTest TRAP-TYPE
		ENTERPRISE	netPrinter
		DESCRIPTION
			"The peripheral is performing an engine 
			 or internal test"
	::= 10016

	periphInfoPrintingDemoPage TRAP-TYPE
		ENTERPRISE	netPrinter
		DESCRIPTION
			"The peripheral is printing the typeface
			 list or font list"
	::= 10017
	
	periphInfoMenuReset TRAP-TYPE
		ENTERPRISE	netPrinter
		DESCRIPTION
			"The peripheral is performing a menu reset"
		
	::= 10018

	periphInfoResetActiveIO TRAP-TYPE
		ENTERPRISE	netPrinter
		DESCRIPTION
			"The peripheral is resetting the I/O channel
			 associated with the active job.  This is 
			 typically done through the front panel menu"
	::= 10019

	periphInfoResetAllIO TRAP-TYPE
		ENTERPRISE	netPrinter
		DESCRIPTION
			"The peripheral is resetting all I/O channels"
	::= 10020

	periphInfoColdReset TRAP-TYPE
		ENTERPRISE	netPrinter
		DESCRIPTION
			"The peripheral is performing a cold-reset, 
			 which clears non-volatile storage"
	::= 10021

	periphInfoPrintingConfigPage TRAP-TYPE
		ENTERPRISE	netPrinter
		DESCRIPTION
			"The peripheral is printing its config page"
	::= 10022

	periphInfoProcessingJob TRAP-TYPE
		ENTERPRISE	netPrinter
		DESCRIPTION
			"The peripheral is processing a job."
	::= 10023

	periphInfoNeedsFormFeed TRAP-TYPE
		ENTERPRISE	netPrinter
		DESCRIPTION
			"The peripheral is waiting for a formfeed."
	::= 10024

	periphInfoAccessDenied TRAP-TYPE
		ENTERPRISE	netPrinter
		DESCRIPTION
			"The peripheral has denied access to the
			 control panel."
	::= 10025

	periphInfoClearingPaperPath TRAP-TYPE
		ENTERPRISE	netPrinter
		DESCRIPTION
			"The peripheral clearing the paper path
			 due to a jam or media misfeed."
	::= 10027

	periphInfoPrintingErrorLog TRAP-TYPE
		ENTERPRISE	netPrinter
		DESCRIPTION
			"The peripheral is printing its error log."
	::= 10028

	periphInfoFormFeeding TRAP-TYPE
		ENTERPRISE	netPrinter
		DESCRIPTION
			"The peripheral is in the process of printing
			 a page due to a form feed."
	::= 10029

	periphInfoJobMessage TRAP-TYPE
		ENTERPRISE	netPrinter
		DESCRIPTION
			"The peripheral is in the process of printing
			 a page with a Job Message."
	::= 10030

	periphInfoCheckingPrinter TRAP-TYPE
		ENTERPRISE	netPrinter
		DESCRIPTION
			"TBD"
	::= 10031

-- Background paper loading messages (BPL) - these messages appear when a 
-- paper input source is out of paper but another paper source is 
-- available and  loaded with the correct paper size.

-- unknown paper  

	periphBPLMPTrayUnknownPaper TRAP-TYPE
		ENTERPRISE	netPrinter
		DESCRIPTION
			"The peripheral is utilizing the MP tray or  			 	
			 multipurpose tray1 with an unknown size paper to 		
			 process the job rather than the tray specified."
	::= 11000

	periphBPLManualFeedUnknownPaper TRAP-TYPE
		ENTERPRISE	netPrinter
		DESCRIPTION
			"The peripheral is utilizing the manual feed with
 			 an unknown size paper to process the job rather 
			 than the tray specified."
	::= 11100

	periphBPLPCTrayUnknownPaper TRAP-TYPE
		ENTERPRISE	netPrinter
		DESCRIPTION
			"The peripheral is utilizing the PC tray, 			 	
			 the upper cassette, or universal tray 2 with
			 an unknown size paper to process the job rather 
			 than the tray specified."
	::= 11200

	periphBPLLCTrayUnknownPaper TRAP-TYPE
		ENTERPRISE	netPrinter
		DESCRIPTION
			"The peripheral is utilizing the LC tray, 			 	
			 the lower cassette, or universal tray 3 with
			 an unknown size paper to process the job rather 
			 than the tray specified."
	::= 11300

	periphBPLEETrayUnknownPaper TRAP-TYPE
		ENTERPRISE	netPrinter
		DESCRIPTION
			"The peripheral is utilizing the EE tray or
			 envelope feeder with an unknown size paper to 
			 process the job rather than the tray specified."
	::= 11400

	periphBPLHCITray4UnknownPaper TRAP-TYPE
		ENTERPRISE	netPrinter
		DESCRIPTION
			"The peripheral is utilizing HCI tray 4 
			 with an unknown size paper to process the job 		
			 rather than the tray specified."
	::= 11500

	periphBPLHCITray5UnknownPaper TRAP-TYPE
		ENTERPRISE	netPrinter
		DESCRIPTION
			"The peripheral is utilizing HCI tray 5 
			 with an unknown size paper to process the job 		
			 rather than the tray specified."
	::= 11600

	periphBPLHCITray6UnknownPaper TRAP-TYPE
		ENTERPRISE	netPrinter
		DESCRIPTION
			"The peripheral is utilizing HCI tray 6 
			 with an unknown size paper to process the job 		
			 rather than the tray specified."
	::= 11700

	periphBPLHCITray7UnknownPaper TRAP-TYPE
		ENTERPRISE	netPrinter
		DESCRIPTION
			"The peripheral is utilizing HCI tray 7 
			 with an unknown size paper to process the job 		
			 rather than the tray specified."
	::= 11800

	periphBPLHCITray8UnknownPaper TRAP-TYPE
		ENTERPRISE	netPrinter
		DESCRIPTION
			"The peripheral is utilizing HCI tray 8 
			 with an unknown size paper to process the job 		
			 rather than the tray specified."
	::= 11900


-- unknown envelope

	periphBPLMPTrayUnknownEnvelope TRAP-TYPE
		ENTERPRISE	netPrinter
		DESCRIPTION
			"The peripheral is utilizing the MP tray or  			 	
			 multipurpose tray1 with an unknown size env. to 		
			 process the job rather than the tray specified."
	::= 11001

	periphBPLManualFeedUnknownEnvelope TRAP-TYPE
		ENTERPRISE	netPrinter
		DESCRIPTION
			"The peripheral is utilizing the manual feed with
 			 an unknown size env. to process the job rather 
			 than the tray specified."
	::= 11101

	periphBPLPCTrayUnknownEnvelope TRAP-TYPE
		ENTERPRISE	netPrinter
		DESCRIPTION
			"The peripheral is utilizing the PC tray, 			 	
			 the upper cassette, or universal tray 2 with
			 an unknown size env. to process the job rather 
			 than the tray specified."
	::= 11201

	periphBPLLCTrayUnknownEnvelope TRAP-TYPE
		ENTERPRISE	netPrinter
		DESCRIPTION
			"The peripheral is utilizing the LC tray, 			 	
			 the lower cassette, or universal tray 3 with
			 an unknown size env. to process the job rather 
			 than the tray specified."
	::= 11301

	periphBPLEETrayUnknownEnvelope TRAP-TYPE
		ENTERPRISE	netPrinter
		DESCRIPTION
			"The peripheral is utilizing the EE tray or
			 envelope feeder with an unknown size env. to 
			 process the job rather than the tray specified."
	::= 11401

	periphBPLHCITray4UnknownEnvelope TRAP-TYPE
		ENTERPRISE	netPrinter
		DESCRIPTION
			"The peripheral is utilizing HCI tray 4
			 with an unknown size env. to process the job 		
			 rather than the tray specified."
	::= 11501

	periphBPLHCITray5UnknownEnvelope TRAP-TYPE
		ENTERPRISE	netPrinter
		DESCRIPTION
			"The peripheral is utilizing HCI tray 5
			 with an unknown size env. to process the job 		
			 rather than the tray specified."
	::= 11601

	periphBPLHCITray6UnknownEnvelope TRAP-TYPE
		ENTERPRISE	netPrinter
		DESCRIPTION
			"The peripheral is utilizing HCI tray 6
			 with an unknown size env. to process the job 		
			 rather than the tray specified."
	::= 11701

	periphBPLHCITray7UnknownEnvelope TRAP-TYPE
		ENTERPRISE	netPrinter
		DESCRIPTION
			"The peripheral is utilizing HCI tray 7
			 with an unknown size env. to process the job 		
			 rather than the tray specified."
	::= 11801

	periphBPLHCITray8UnknownEnvelope TRAP-TYPE
		ENTERPRISE	netPrinter
		DESCRIPTION
			"The peripheral is utilizing HCI tray 8
			 with an unknown size env. to process the job 		
			 rather than the tray specified."
	::= 11901

-- Letter Paper

	periphBPLMPTrayLetterPaper TRAP-TYPE
		ENTERPRISE	netPrinter
		DESCRIPTION
			"The peripheral is utilizing the MP tray or  			 	
			 multipurpose tray1 with letter paper to 		
			 process the job rather than the tray specified."
	::= 11002

	periphBPLManualFeedLetterPaper TRAP-TYPE
		ENTERPRISE	netPrinter
		DESCRIPTION
			"The peripheral is utilizing the manual feed with
 			 letter paper to process the job rather 
			 than the tray specified."
	::= 11102

	periphBPLPCTrayLetterPaper TRAP-TYPE
		ENTERPRISE	netPrinter
		DESCRIPTION
			"The peripheral is utilizing the PC tray, 			 	
			 the upper cassette, or universal tray 2 with
			 letter paper to process the job rather 
			 than the tray specified."
	::= 11202

	periphBPLLCTrayLetterPaper TRAP-TYPE
		ENTERPRISE	netPrinter
		DESCRIPTION
			"The peripheral is utilizing the LC tray, 			 	
			 the lower cassette, or universal tray 3 with
			 letter paper to process the job rather 
			 than the tray specified."
	::= 11302

	periphBPLEETrayLetterPaper TRAP-TYPE
		ENTERPRISE	netPrinter
		DESCRIPTION
			"The peripheral is utilizing the EE tray or
			 envelope feeder with letter paper to 
			 process the job rather than the tray specified."
	::= 11402

	periphBPLHCITray4LetterPaper TRAP-TYPE
		ENTERPRISE	netPrinter
		DESCRIPTION
			"The peripheral is utilizing HCI tray 4
			 with letter paper to process the job 		
			 rather than the tray specified."
	::= 11502

	periphBPLHCITray5LetterPaper TRAP-TYPE
		ENTERPRISE	netPrinter
		DESCRIPTION
			"The peripheral is utilizing HCI tray 5
			 with letter paper to process the job 		
			 rather than the tray specified."
	::= 11602

	periphBPLHCITray6LetterPaper TRAP-TYPE
		ENTERPRISE	netPrinter
		DESCRIPTION
			"The peripheral is utilizing HCI tray 6
			 with letter paper to process the job 		
			 rather than the tray specified."
	::= 11702

	periphBPLHCITray7LetterPaper TRAP-TYPE
		ENTERPRISE	netPrinter
		DESCRIPTION
			"The peripheral is utilizing HCI tray 7
			 with letter paper to process the job 		
			 rather than the tray specified."
	::= 11802

	periphBPLHCITray8LetterPaper TRAP-TYPE
		ENTERPRISE	netPrinter
		DESCRIPTION
			"The peripheral is utilizing HCI tray 8
			 with letter paper to process the job 		
			 rather than the tray specified."
	::= 11902

-- Legal Paper

	periphBPLMPTrayLegalPaper TRAP-TYPE
		ENTERPRISE	netPrinter
		DESCRIPTION
			"The peripheral is utilizing the MP tray or  			 	
			 multipurpose tray1 with legal paper to 		
			 process the job rather than the tray specified."
	::= 11003

	periphBPLManualFeedLegalPaper TRAP-TYPE
		ENTERPRISE	netPrinter
		DESCRIPTION
			"The peripheral is utilizing the manual feed with
 			 legal paper to process the job rather 
			 than the tray specified."
	::= 11103

	periphBPLPCTrayLegalPaper TRAP-TYPE
		ENTERPRISE	netPrinter
		DESCRIPTION
			"The peripheral is utilizing the PC tray, 			 	
			 the upper cassette, or universal tray 2 with
			 legal paper to process the job rather 
			 than the tray specified."
	::= 11203

	periphBPLLCTrayLegalPaper TRAP-TYPE
		ENTERPRISE	netPrinter
		DESCRIPTION
			"The peripheral is utilizing the LC tray, 			 	
			 the lower cassette, or universal tray 3 with
			 legal paper to process the job rather 
			 than the tray specified."
	::= 11303

	periphBPLEETrayLegalPaper TRAP-TYPE
		ENTERPRISE	netPrinter
		DESCRIPTION
			"The peripheral is utilizing the EE tray or
			 envelope feeder with legal paper to 
			 process the job rather than the tray specified."
	::= 11403

	periphBPLHCITray4LegalPaper TRAP-TYPE
		ENTERPRISE	netPrinter
		DESCRIPTION
			"The peripheral is utilizing HCI tray 4
			 with legal paper to process the job 		
			 rather than the tray specified."
	::= 11503

	periphBPLHCITray5LegalPaper TRAP-TYPE
		ENTERPRISE	netPrinter
		DESCRIPTION
			"The peripheral is utilizing HCI tray 5
			 with legal paper to process the job 		
			 rather than the tray specified."
	::= 11603

	periphBPLHCITray6LegalPaper TRAP-TYPE
		ENTERPRISE	netPrinter
		DESCRIPTION
			"The peripheral is utilizing HCI tray 6
			 with legal paper to process the job 		
			 rather than the tray specified."
	::= 11703

	periphBPLHCITray7LegalPaper TRAP-TYPE
		ENTERPRISE	netPrinter
		DESCRIPTION
			"The peripheral is utilizing HCI tray 7
			 with legal paper to process the job 		
			 rather than the tray specified."
	::= 11803

	periphBPLHCITray8LegalPaper TRAP-TYPE
		ENTERPRISE	netPrinter
		DESCRIPTION
			"The peripheral is utilizing HCI tray 8
			 with legal paper to process the job 		
			 rather than the tray specified."
	::= 11903


-- A4 Paper

	periphBPLMPTrayA4Paper TRAP-TYPE
		ENTERPRISE	netPrinter
		DESCRIPTION
			"The peripheral is utilizing the MP tray or  			 	
			 multipurpose tray1 with A4 paper to 		
			 process the job rather than the tray specified."
	::= 11004

	periphBPLManualFeedA4Paper TRAP-TYPE
		ENTERPRISE	netPrinter
		DESCRIPTION
			"The peripheral is utilizing the manual feed with
 			 A4 paper to process the job rather 
			 than the tray specified."
	::= 11104

	periphBPLPCTrayA4Paper TRAP-TYPE
		ENTERPRISE	netPrinter
		DESCRIPTION
			"The peripheral is utilizing the PC tray, 			 	
			 the upper cassette, or universal tray 2 with
			 A4 paper to process the job rather 
			 than the tray specified."
	::= 11204

	periphBPLLCTrayA4Paper TRAP-TYPE
		ENTERPRISE	netPrinter
		DESCRIPTION
			"The peripheral is utilizing the LC tray, 			 	
			 the lower cassette, or universal tray 3 with
			 A4 paper to process the job rather 
			 than the tray specified."
	::= 11304

	periphBPLEETrayA4Paper TRAP-TYPE
		ENTERPRISE	netPrinter
		DESCRIPTION
			"The peripheral is utilizing the EE tray or
			 envelope feeder with A4 paper to 
			 process the job rather than the tray specified."
	::= 11404

	periphBPLHCITray4A4Paper TRAP-TYPE
		ENTERPRISE	netPrinter
		DESCRIPTION
			"The peripheral is utilizing HCI tray 4
			 with A4 paper to process the job 		
			 rather than the tray specified."
	::= 11504

	periphBPLHCITray5A4Paper TRAP-TYPE
		ENTERPRISE	netPrinter
		DESCRIPTION
			"The peripheral is utilizing HCI tray 5
			 with A4 paper to process the job 		
			 rather than the tray specified."
	::= 11604

	periphBPLHCITray6A4Paper TRAP-TYPE
		ENTERPRISE	netPrinter
		DESCRIPTION
			"The peripheral is utilizing HCI tray 6
			 with A4 paper to process the job 		
			 rather than the tray specified."
	::= 11704

	periphBPLHCITray7A4Paper TRAP-TYPE
		ENTERPRISE	netPrinter
		DESCRIPTION
			"The peripheral is utilizing HCI tray 7
			 with A4 paper to process the job 		
			 rather than the tray specified."
	::= 11804

	periphBPLHCITray8A4Paper TRAP-TYPE
		ENTERPRISE	netPrinter
		DESCRIPTION
			"The peripheral is utilizing HCI tray 8
			 with A4 paper to process the job 		
			 rather than the tray specified."
	::= 11904

-- Executive Paper

	periphBPLMPTrayExecutivePaper TRAP-TYPE
		ENTERPRISE	netPrinter
		DESCRIPTION
			"The peripheral is utilizing the MP tray or  			 	
			 multipurpose tray1 with executive paper to 		
			 process the job rather than the tray specified."
	::= 11005

	periphBPLManualFeedExecutivePaper TRAP-TYPE
		ENTERPRISE	netPrinter
		DESCRIPTION
			"The peripheral is utilizing the manual feed with
 			 executive paper to process the job rather 
			 than the tray specified."
	::= 11105

	periphBPLPCTrayExecutivePaper TRAP-TYPE
		ENTERPRISE	netPrinter
		DESCRIPTION
			"The peripheral is utilizing the PC tray, 			 	
			 the upper cassette, or universal tray 2 with
			 executive paper to process the job rather 
			 than the tray specified."
	::= 11205

	periphBPLLCTrayExecutivePaper TRAP-TYPE
		ENTERPRISE	netPrinter
		DESCRIPTION
			"The peripheral is utilizing the LC tray, 			 	
			 the lower cassette, or universal tray 3 with
			 executive paper to process the job rather 
			 than the tray specified."
	::= 11305

	periphBPLEETrayExecutivePaper TRAP-TYPE
		ENTERPRISE	netPrinter
		DESCRIPTION
			"The peripheral is utilizing the EE tray or
			 envelope feeder with executive paper to 
			 process the job rather than the tray specified."
	::= 11405

	periphBPLHCITray4ExecutivePaper TRAP-TYPE
		ENTERPRISE	netPrinter
		DESCRIPTION
			"The peripheral is utilizing HCI tray 4
			 with executive paper to process the job 		
			 rather than the tray specified."
	::= 11505

	periphBPLHCITray5ExecutivePaper TRAP-TYPE
		ENTERPRISE	netPrinter
		DESCRIPTION
			"The peripheral is utilizing HCI tray 5
			 with executive paper to process the job 		
			 rather than the tray specified."
	::= 11605

	periphBPLHCITray6ExecutivePaper TRAP-TYPE
		ENTERPRISE	netPrinter
		DESCRIPTION
			"The peripheral is utilizing HCI tray 6
			 with executive paper to process the job 		
			 rather than the tray specified."
	::= 11705

	periphBPLHCITray7ExecutivePaper TRAP-TYPE
		ENTERPRISE	netPrinter
		DESCRIPTION
			"The peripheral is utilizing HCI tray 7
			 with executive paper to process the job 		
			 rather than the tray specified."
	::= 11805

	periphBPLHCITray8ExecutivePaper TRAP-TYPE
		ENTERPRISE	netPrinter
		DESCRIPTION
			"The peripheral is utilizing HCI tray 8
			 with executive paper to process the job 		
			 rather than the tray specified."
	::= 11905

-- Ledger Paper

	periphBPLMPTrayLedgerPaper TRAP-TYPE
		ENTERPRISE	netPrinter
		DESCRIPTION
			"The peripheral is utilizing the MP tray or  			 	
			 multipurpose tray1 with Ledger paper to 		
			 process the job rather than the tray specified."
	::= 11006

	periphBPLManualFeedLedgerPaper TRAP-TYPE
		ENTERPRISE	netPrinter
		DESCRIPTION
			"The peripheral is utilizing the manual feed with
 			 Ledger paper to process the job rather 
			 than the tray specified."
	::= 11106

	periphBPLPCTrayLedgerPaper TRAP-TYPE
		ENTERPRISE	netPrinter
		DESCRIPTION
			"The peripheral is utilizing the PC tray, 			 	
			 the upper cassette, or universal tray 2 with
			 Ledger paper to process the job rather 
			 than the tray specified."
	::= 11206

	periphBPLLCTrayLedgerPaper TRAP-TYPE
		ENTERPRISE	netPrinter
		DESCRIPTION
			"The peripheral is utilizing the LC tray, 			 	
			 the lower cassette, or universal tray 3 with
			 Ledger paper to process the job rather 
			 than the tray specified."
	::= 11306

	periphBPLEETrayLedgerPaper TRAP-TYPE
		ENTERPRISE	netPrinter
		DESCRIPTION
			"The peripheral is utilizing the EE tray or
			 envelope feeder with Ledger paper to 
			 process the job rather than the tray specified."
	::= 11406

	periphBPLHCITray4LedgerPaper TRAP-TYPE
		ENTERPRISE	netPrinter
		DESCRIPTION
			"The peripheral is utilizing HCI tray 4
			 with Ledger paper to process the job 		
			 rather than the tray specified."
	::= 11506

	periphBPLHCITray5LedgerPaper TRAP-TYPE
		ENTERPRISE	netPrinter
		DESCRIPTION
			"The peripheral is utilizing HCI tray 5
			 with Ledger paper to process the job 		
			 rather than the tray specified."
	::= 11606

	periphBPLHCITray6LedgerPaper TRAP-TYPE
		ENTERPRISE	netPrinter
		DESCRIPTION
			"The peripheral is utilizing HCI tray 6
			 with Ledger paper to process the job 		
			 rather than the tray specified."
	::= 11706

	periphBPLHCITray7LedgerPaper TRAP-TYPE
		ENTERPRISE	netPrinter
		DESCRIPTION
			"The peripheral is utilizing HCI tray 7
			 with Ledger paper to process the job 		
			 rather than the tray specified."
	::= 11806

	periphBPLHCITray8LedgerPaper TRAP-TYPE
		ENTERPRISE	netPrinter
		DESCRIPTION
			"The peripheral is utilizing HCI tray 8
			 with Ledger paper to process the job 		
			 rather than the tray specified."
	::= 11906

-- A3 Paper

	periphBPLMPTrayA3Paper TRAP-TYPE
		ENTERPRISE	netPrinter
		DESCRIPTION
			"The peripheral is utilizing the MP tray or  			 	
			 multipurpose tray1 with A3 paper to 		
			 process the job rather than the tray specified."
	::= 11007

	periphBPLManualFeedA3Paper TRAP-TYPE
		ENTERPRISE	netPrinter
		DESCRIPTION
			"The peripheral is utilizing the manual feed with
 			 A3 paper to process the job rather 
			 than the tray specified."
	::= 11107

	periphBPLPCTrayA3Paper TRAP-TYPE
		ENTERPRISE	netPrinter
		DESCRIPTION
			"The peripheral is utilizing the PC tray, 			 	
			 the upper cassette, or universal tray 2 with
			 A3 paper to process the job rather 
			 than the tray specified."
	::= 11207

	periphBPLLCTrayA3Paper TRAP-TYPE
		ENTERPRISE	netPrinter
		DESCRIPTION
			"The peripheral is utilizing the LC tray, 			 	
			 the lower cassette, or universal tray 3 with
			 A3 paper to process the job rather 
			 than the tray specified."
	::= 11307

	periphBPLEETrayA3Paper TRAP-TYPE
		ENTERPRISE	netPrinter
		DESCRIPTION
			"The peripheral is utilizing the EE tray or
			 envelope feeder with A3 paper to 
			 process the job rather than the tray specified."
	::= 11407

	periphBPLHCITray4A3Paper TRAP-TYPE
		ENTERPRISE	netPrinter
		DESCRIPTION
			"The peripheral is utilizing HCI tray 4 
			 with A3 paper to process the job 		
			 rather than the tray specified."
	::= 11507

	periphBPLHCITray5A3Paper TRAP-TYPE
		ENTERPRISE	netPrinter
		DESCRIPTION
			"The peripheral is utilizing HCI tray 5 
			 with A3 paper to process the job 		
			 rather than the tray specified."
	::= 11607

	periphBPLHCITray6A3Paper TRAP-TYPE
		ENTERPRISE	netPrinter
		DESCRIPTION
			"The peripheral is utilizing HCI tray 6 
			 with A3 paper to process the job 		
			 rather than the tray specified."
	::= 11707

	periphBPLHCITray7A3Paper TRAP-TYPE
		ENTERPRISE	netPrinter
		DESCRIPTION
			"The peripheral is utilizing HCI tray 7 
			 with A3 paper to process the job 		
			 rather than the tray specified."
	::= 11807

	periphBPLHCITray8A3Paper TRAP-TYPE
		ENTERPRISE	netPrinter
		DESCRIPTION
			"The peripheral is utilizing HCI tray 8 
			 with A3 paper to process the job 		
			 rather than the tray specified."
	::= 11907

-- COM10 envelope

	periphBPLMPTrayCOM10Envelope TRAP-TYPE
		ENTERPRISE	netPrinter
		DESCRIPTION
			"The peripheral is utilizing the MP tray or  			 	
			 multipurpose tray1 with an COM10 size env. to 		
			 process the job rather than the tray specified."
	::= 11008

	periphBPLManualFeedCOM10Envelope TRAP-TYPE
		ENTERPRISE	netPrinter
		DESCRIPTION
			"The peripheral is utilizing the manual feed with
 			 an COM10 size env. to process the job rather 
			 than the tray specified."
	::= 11108

	periphBPLPCTrayCOM10Envelope TRAP-TYPE
		ENTERPRISE	netPrinter
		DESCRIPTION
			"The peripheral is utilizing the PC tray, 			 	
			 the upper cassette, or universal tray 2 with
			 an COM10 size env. to process the job rather 
			 than the tray specified."
	::= 11208

	periphBPLLCTrayCOM10Envelope TRAP-TYPE
		ENTERPRISE	netPrinter
		DESCRIPTION
			"The peripheral is utilizing the LC tray, 			 	
			 the lower cassette, or universal tray 3 with
			 an COM10 size env. to process the job rather 
			 than the tray specified."
	::= 11308

	periphBPLEETrayCOM10Envelope TRAP-TYPE
		ENTERPRISE	netPrinter
		DESCRIPTION
			"The peripheral is utilizing the EE tray or
			 envelope feeder with an COM10 size env. to 
			 process the job rather than the tray specified."
	::= 11408

	periphBPLHCITray4COM10Envelope TRAP-TYPE
		ENTERPRISE	netPrinter
		DESCRIPTION
			"The peripheral is utilizing HCI tray 4
			 with an COM10 size env. to process the job 		
			 rather than the tray specified."
	::= 11508

	periphBPLHCITray5COM10Envelope TRAP-TYPE
		ENTERPRISE	netPrinter
		DESCRIPTION
			"The peripheral is utilizing HCI tray 5
			 with an COM10 size env. to process the job 		
			 rather than the tray specified."
	::= 11608

	periphBPLHCITray6COM10Envelope TRAP-TYPE
		ENTERPRISE	netPrinter
		DESCRIPTION
			"The peripheral is utilizing HCI tray 6
			 with an COM10 size env. to process the job 		
			 rather than the tray specified."
	::= 11708

	periphBPLHCITray7COM10Envelope TRAP-TYPE
		ENTERPRISE	netPrinter
		DESCRIPTION
			"The peripheral is utilizing HCI tray 7
			 with an COM10 size env. to process the job 		
			 rather than the tray specified."
	::= 11808

	periphBPLHCITray8COM10Envelope TRAP-TYPE
		ENTERPRISE	netPrinter
		DESCRIPTION
			"The peripheral is utilizing HCI tray 8
			 with an COM10 size env. to process the job 		
			 rather than the tray specified."
	::= 11908

-- Monarch envelope

	periphBPLMPTrayMonarchEnvelope TRAP-TYPE
		ENTERPRISE	netPrinter
		DESCRIPTION
			"The peripheral is utilizing the MP tray or  			 	
			 multipurpose tray1 with an Monarch size env. to 		
			 process the job rather than the tray specified."
	::= 11009

	periphBPLManualFeedMonarchEnvelope TRAP-TYPE
		ENTERPRISE	netPrinter
		DESCRIPTION
			"The peripheral is utilizing the manual feed with
 			 an Monarch size env. to process the job rather 
			 than the tray specified."
	::= 11109

	periphBPLPCTrayMonarchEnvelope TRAP-TYPE
		ENTERPRISE	netPrinter
		DESCRIPTION
			"The peripheral is utilizing the PC tray, 			 	
			 the upper cassette, or universal tray 2 with
			 an Monarch size env. to process the job rather 
			 than the tray specified."
	::= 11209

	periphBPLLCTrayMonarchEnvelope TRAP-TYPE
		ENTERPRISE	netPrinter
		DESCRIPTION
			"The peripheral is utilizing the LC tray, 			 	
			 the lower cassette, or universal tray 3 with
			 an Monarch size env. to process the job rather 
			 than the tray specified."
	::= 11309

	periphBPLEETrayMonarchEnvelope TRAP-TYPE
		ENTERPRISE	netPrinter
		DESCRIPTION
			"The peripheral is utilizing the EE tray or
			 envelope feeder with an Monarch size env. to 
			 process the job rather than the tray specified."
	::= 11409

	periphBPLHCITray4MonarchEnvelope TRAP-TYPE
		ENTERPRISE	netPrinter
		DESCRIPTION
			"The peripheral is utilizing HCI tray 4
			 with an Monarch size env. to process the job 		
			 rather than the tray specified."
	::= 11509

	periphBPLHCITray5MonarchEnvelope TRAP-TYPE
		ENTERPRISE	netPrinter
		DESCRIPTION
			"The peripheral is utilizing HCI tray 5
			 with an Monarch size env. to process the job 		
			 rather than the tray specified."
	::= 11609

	periphBPLHCITray6MonarchEnvelope TRAP-TYPE
		ENTERPRISE	netPrinter
		DESCRIPTION
			"The peripheral is utilizing HCI tray 6
			 with an Monarch size env. to process the job 		
			 rather than the tray specified."
	::= 11709

	periphBPLHCITray7MonarchEnvelope TRAP-TYPE
		ENTERPRISE	netPrinter
		DESCRIPTION
			"The peripheral is utilizing HCI tray 7
			 with an Monarch size env. to process the job 		
			 rather than the tray specified."
	::= 11809

	periphBPLHCITray8MonarchEnvelope TRAP-TYPE
		ENTERPRISE	netPrinter
		DESCRIPTION
			"The peripheral is utilizing HCI tray 8
			 with an Monarch size env. to process the job 		
			 rather than the tray specified."
	::= 11909

-- C5 envelope

	periphBPLMPTrayC5Envelope TRAP-TYPE
		ENTERPRISE	netPrinter
		DESCRIPTION
			"The peripheral is utilizing the MP tray or  			 	
			 multipurpose tray1 with an C5 size env. to 		
			 process the job rather than the tray specified."
	::= 11010

	periphBPLManualFeedC5Envelope TRAP-TYPE
		ENTERPRISE	netPrinter
		DESCRIPTION
			"The peripheral is utilizing the manual feed with
 			 an C5 size env. to process the job rather 
			 than the tray specified."
	::= 11110

	periphBPLPCTrayC5Envelope TRAP-TYPE
		ENTERPRISE	netPrinter
		DESCRIPTION
			"The peripheral is utilizing the PC tray, 			 	
			 the upper cassette, or universal tray 2 with
			 an C5 size env. to process the job rather 
			 than the tray specified."
	::= 11210

	periphBPLLCTrayC5Envelope TRAP-TYPE
		ENTERPRISE	netPrinter
		DESCRIPTION
			"The peripheral is utilizing the LC tray, 			 	
			 the lower cassette, or universal tray 3 with
			 an C5 size env. to process the job rather 
			 than the tray specified."
	::= 11310

	periphBPLEETrayC5Envelope TRAP-TYPE
		ENTERPRISE	netPrinter
		DESCRIPTION
			"The peripheral is utilizing the EE tray or
			 envelope feeder with an C5 size env. to 
			 process the job rather than the tray specified."
	::= 11410

	periphBPLHCITray4C5Envelope TRAP-TYPE
		ENTERPRISE	netPrinter
		DESCRIPTION
			"The peripheral is utilizing HCI tray 4
			 with an C5 size env. to process the job 		
			 rather than the tray specified."
	::= 11510

	periphBPLHCITray5C5Envelope TRAP-TYPE
		ENTERPRISE	netPrinter
		DESCRIPTION
			"The peripheral is utilizing HCI tray 5
			 with an C5 size env. to process the job 		
			 rather than the tray specified."
	::= 11610

	periphBPLHCITray6C5Envelope TRAP-TYPE
		ENTERPRISE	netPrinter
		DESCRIPTION
			"The peripheral is utilizing HCI tray 6
			 with an C5 size env. to process the job 		
			 rather than the tray specified."
	::= 11710

	periphBPLHCITray7C5Envelope TRAP-TYPE
		ENTERPRISE	netPrinter
		DESCRIPTION
			"The peripheral is utilizing HCI tray 7
			 with an C5 size env. to process the job 		
			 rather than the tray specified."
	::= 11810

	periphBPLHCITray8C5Envelope TRAP-TYPE
		ENTERPRISE	netPrinter
		DESCRIPTION
			"The peripheral is utilizing HCI tray 8
			 with an C5 size env. to process the job 		
			 rather than the tray specified."
	::= 11910


-- DL envelope

	periphBPLMPTrayDLEnvelope TRAP-TYPE
		ENTERPRISE	netPrinter
		DESCRIPTION
			"The peripheral is utilizing the MP tray or  			 	
			 multipurpose tray1 with an DL size env. to 		
			 process the job rather than the tray specified."
	::= 11011

	periphBPLManualFeedDLEnvelope TRAP-TYPE
		ENTERPRISE	netPrinter
		DESCRIPTION
			"The peripheral is utilizing the manual feed with
 			 an DL size env. to process the job rather 
			 than the tray specified."
	::= 11111

	periphBPLPCTrayDLEnvelope TRAP-TYPE
		ENTERPRISE	netPrinter
		DESCRIPTION
			"The peripheral is utilizing the PC tray, 			 	
			 the upper cassette, or universal tray 2 with
			 an DL size env. to process the job rather 
			 than the tray specified."
	::= 11211

	periphBPLLCTrayDLEnvelope TRAP-TYPE
		ENTERPRISE	netPrinter
		DESCRIPTION
			"The peripheral is utilizing the LC tray, 			 	
			 the lower cassette, or universal tray 3 with
			 an DL size env. to process the job rather 
			 than the tray specified."
	::= 11311

	periphBPLEETrayDLEnvelope TRAP-TYPE
		ENTERPRISE	netPrinter
		DESCRIPTION
			"The peripheral is utilizing the EE tray or
			 envelope feeder with an DL size env. to 
			 process the job rather than the tray specified."
	::= 11411

	periphBPLHCITray4DLEnvelope TRAP-TYPE
		ENTERPRISE	netPrinter
		DESCRIPTION
			"The peripheral is utilizing HCI tray 4
			 with an DL size env. to process the job 		
			 rather than the tray specified."
	::= 11511

	periphBPLHCITray5DLEnvelope TRAP-TYPE
		ENTERPRISE	netPrinter
		DESCRIPTION
			"The peripheral is utilizing HCI tray 5
			 with an DL size env. to process the job 		
			 rather than the tray specified."
	::= 11611

	periphBPLHCITray6DLEnvelope TRAP-TYPE
		ENTERPRISE	netPrinter
		DESCRIPTION
			"The peripheral is utilizing HCI tray 6
			 with an DL size env. to process the job 		
			 rather than the tray specified."
	::= 11711

	periphBPLHCITray7DLEnvelope TRAP-TYPE
		ENTERPRISE	netPrinter
		DESCRIPTION
			"The peripheral is utilizing HCI tray 7
			 with an DL size env. to process the job 		
			 rather than the tray specified."
	::= 11811

	periphBPLHCITray8DLEnvelope TRAP-TYPE
		ENTERPRISE	netPrinter
		DESCRIPTION
			"The peripheral is utilizing HCI tray 8
			 with an DL size env. to process the job 		
			 rather than the tray specified."
	::= 11911


-- JISB4 Paper

	periphBPLMPTrayJISB4Paper TRAP-TYPE
		ENTERPRISE	netPrinter
		DESCRIPTION
			"The peripheral is utilizing the MP tray or  			 	
			 multipurpose tray1 with JISB4 paper to 		
			 process the job rather than the tray specified."
	::= 11012

	periphBPLManualFeedJISB4Paper TRAP-TYPE
		ENTERPRISE	netPrinter
		DESCRIPTION
			"The peripheral is utilizing the manual feed with
 			 JISB4 paper to process the job rather 
			 than the tray specified."
	::= 11112

	periphBPLPCTrayJISB4Paper TRAP-TYPE
		ENTERPRISE	netPrinter
		DESCRIPTION
			"The peripheral is utilizing the PC tray, 			 	
			 the upper cassette, or universal tray 2 with
			 JISB4 paper to process the job rather 
			 than the tray specified."
	::= 11212

	periphBPLLCTrayJISB4Paper TRAP-TYPE
		ENTERPRISE	netPrinter
		DESCRIPTION
			"The peripheral is utilizing the LC tray, 			 	
			 the lower cassette, or universal tray 3 with
			 JISB4 paper to process the job rather 
			 than the tray specified."
	::= 11312

	periphBPLEETrayJISB4Paper TRAP-TYPE
		ENTERPRISE	netPrinter
		DESCRIPTION
			"The peripheral is utilizing the EE tray or
			 envelope feeder with JISB4 paper to 
			 process the job rather than the tray specified."
	::= 11412

	periphBPLHCITray4JISB4Paper TRAP-TYPE
		ENTERPRISE	netPrinter
		DESCRIPTION
			"The peripheral is utilizing HCI tray 4
			 with JISB4 paper to process the job 		
			 rather than the tray specified."
	::= 11512

	periphBPLHCITray5JISB4Paper TRAP-TYPE
		ENTERPRISE	netPrinter
		DESCRIPTION
			"The peripheral is utilizing HCI tray 5
			 with JISB4 paper to process the job 		
			 rather than the tray specified."
	::= 11612

	periphBPLHCITray6JISB4Paper TRAP-TYPE
		ENTERPRISE	netPrinter
		DESCRIPTION
			"The peripheral is utilizing HCI tray 6
			 with JISB4 paper to process the job 		
			 rather than the tray specified."
	::= 11712

	periphBPLHCITray7JISB4Paper TRAP-TYPE
		ENTERPRISE	netPrinter
		DESCRIPTION
			"The peripheral is utilizing HCI tray 7
			 with JISB4 paper to process the job 		
			 rather than the tray specified."
	::= 11812

	periphBPLHCITray8JISB4Paper TRAP-TYPE
		ENTERPRISE	netPrinter
		DESCRIPTION
			"The peripheral is utilizing HCI tray 8
			 with JISB4 paper to process the job 		
			 rather than the tray specified."
	::= 11912


-- JISB5 Paper

	periphBPLMPTrayJISB5Paper TRAP-TYPE
		ENTERPRISE	netPrinter
		DESCRIPTION
			"The peripheral is utilizing the MP tray or  			 	
			 multipurpose tray1 with JISB5 paper to 		
			 process the job rather than the tray specified."
	::= 11013

	periphBPLManualFeedJISB5Paper TRAP-TYPE
		ENTERPRISE	netPrinter
		DESCRIPTION
			"The peripheral is utilizing the manual feed with
 			 JISB5 paper to process the job rather 
			 than the tray specified."
	::= 11113

	periphBPLPCTrayJISB5Paper TRAP-TYPE
		ENTERPRISE	netPrinter
		DESCRIPTION
			"The peripheral is utilizing the PC tray, 			 	
			 the upper cassette, or universal tray 2 with
			 JISB5 paper to process the job rather 
			 than the tray specified."
	::= 11213

	periphBPLLCTrayJISB5Paper TRAP-TYPE
		ENTERPRISE	netPrinter
		DESCRIPTION
			"The peripheral is utilizing the LC tray, 			 	
			 the lower cassette, or universal tray 3 with
			 JISB5 paper to process the job rather 
			 than the tray specified."
	::= 11313

	periphBPLEETrayJISB5Paper TRAP-TYPE
		ENTERPRISE	netPrinter
		DESCRIPTION
			"The peripheral is utilizing the EE tray or
			 envelope feeder with JISB5 paper to 
			 process the job rather than the tray specified."
	::= 11413

	periphBPLHCITray4JISB5Paper TRAP-TYPE
		ENTERPRISE	netPrinter
		DESCRIPTION
			"The peripheral is utilizing HCI tray 4
			 with JISB5 paper to process the job 		
			 rather than the tray specified."
	::= 11513

	periphBPLHCITray5JISB5Paper TRAP-TYPE
		ENTERPRISE	netPrinter
		DESCRIPTION
			"The peripheral is utilizing HCI tray 5
			 with JISB5 paper to process the job 		
			 rather than the tray specified."
	::= 11613

	periphBPLHCITray6JISB5Paper TRAP-TYPE
		ENTERPRISE	netPrinter
		DESCRIPTION
			"The peripheral is utilizing HCI tray 6
			 with JISB5 paper to process the job 		
			 rather than the tray specified."
	::= 11713

	periphBPLHCITray7JISB5Paper TRAP-TYPE
		ENTERPRISE	netPrinter
		DESCRIPTION
			"The peripheral is utilizing HCI tray 7
			 with JISB5 paper to process the job 		
			 rather than the tray specified."
	::= 11813

	periphBPLHCITray8JISB5Paper TRAP-TYPE
		ENTERPRISE	netPrinter
		DESCRIPTION
			"The peripheral is utilizing HCI tray 8
			 with JISB5 paper to process the job 		
			 rather than the tray specified."
	::= 11913


-- International B5 envelope

	periphBPLMPTrayInternationalB5Envelope TRAP-TYPE
		ENTERPRISE	netPrinter
		DESCRIPTION
			"The peripheral is utilizing the MP tray or  			 	
			 multipurpose tray1 with an International B5 size env. to 		
			 process the job rather than the tray specified."
	::= 11014

	periphBPLManualFeedInternationalB5Envelope TRAP-TYPE
		ENTERPRISE	netPrinter
		DESCRIPTION
			"The peripheral is utilizing the manual feed with
 			 an InternationalB5 size env. to process the job rather 
			 than the tray specified."
	::= 11114

	periphBPLPCTrayInternationalB5Envelope TRAP-TYPE
		ENTERPRISE	netPrinter
		DESCRIPTION
			"The peripheral is utilizing the PC tray, 			 	
			 the upper cassette, or universal tray 2 with
			 an International B5 size env. to process the job rather 
			 than the tray specified."
	::= 11214

	periphBPLLCTrayInternationalB5Envelope TRAP-TYPE
		ENTERPRISE	netPrinter
		DESCRIPTION
			"The peripheral is utilizing the LC tray, 			 	
			 the lower cassette, or universal tray 3 with
			 an International B5 size env. to process the job rather 
			 than the tray specified."
	::= 11314

	periphBPLEETrayInternationalB5Envelope TRAP-TYPE
		ENTERPRISE	netPrinter
		DESCRIPTION
			"The peripheral is utilizing the EE tray or
			 envelope feeder with an International B5 size env. to 
			 process the job rather than the tray specified."
	::= 11414

	periphBPLHCITray4InternationalB5Envelope TRAP-TYPE
		ENTERPRISE	netPrinter
		DESCRIPTION
			"The peripheral is utilizing HCI tray 4 
			 with an International B5 size env. to process the job 		
			 rather than the tray specified."
	::= 11514

	periphBPLHCITray5InternationalB5Envelope TRAP-TYPE
		ENTERPRISE	netPrinter
		DESCRIPTION
			"The peripheral is utilizing HCI tray 5
			 with an International B5 size env. to process the job 		
			 rather than the tray specified."
	::= 11614

	periphBPLHCITray6InternationalB5Envelope TRAP-TYPE
		ENTERPRISE	netPrinter
		DESCRIPTION
			"The peripheral is utilizing HCI tray 6
			 with an International B5 size env. to process the job 		
			 rather than the tray specified."
	::= 11714

	periphBPLHCITray7InternationalB5Envelope TRAP-TYPE
		ENTERPRISE	netPrinter
		DESCRIPTION
			"The peripheral is utilizing HCI tray 7
			 with an International B5 size env. to process the job 		
			 rather than the tray specified."
	::= 11814

	periphBPLHCITray8InternationalB5Envelope TRAP-TYPE
		ENTERPRISE	netPrinter
		DESCRIPTION
			"The peripheral is utilizing HCI tray 8
			 with an International B5 size env. to process the job 		
			 rather than the tray specified."
	::= 11914


-- Custom Media

	periphBPLMPTrayCustomMedia TRAP-TYPE
		ENTERPRISE	netPrinter
		DESCRIPTION
			"The peripheral is utilizing the MP tray or  			 	
			 multipurpose tray1 with Custom Media to 		
			 process the job rather than the tray specified."
	::= 11015

	periphBPLManualFeedCustomMedia TRAP-TYPE
		ENTERPRISE	netPrinter
		DESCRIPTION
			"The peripheral is utilizing the manual feed with
 			 Custom Media to process the job rather 
			 than the tray specified."
	::= 11115

	periphBPLPCTrayCustomMedia TRAP-TYPE
		ENTERPRISE	netPrinter
		DESCRIPTION
			"The peripheral is utilizing the PC tray, 			 	
			 the upper cassette, or universal tray 2 with
			 Custom Media to process the job rather 
			 than the tray specified."
	::= 11215

	periphBPLLCTrayCustomMedia TRAP-TYPE
		ENTERPRISE	netPrinter
		DESCRIPTION
			"The peripheral is utilizing the LC tray, 			 	
			 the lower cassette, or universal tray 3 with
			 Custom Media to process the job rather 
			 than the tray specified."
	::= 11315

	periphBPLEETrayCustomMedia TRAP-TYPE
		ENTERPRISE	netPrinter
		DESCRIPTION
			"The peripheral is utilizing the EE tray or
			 envelope feeder with Custom Media to 
			 process the job rather than the tray specified."
	::= 11415

	periphBPLHCITray4CustomMedia TRAP-TYPE
		ENTERPRISE	netPrinter
		DESCRIPTION
			"The peripheral is utilizing HCI tray 4
			 with Custom Media to process the job 		
			 rather than the tray specified."
	::= 11515

	periphBPLHCITray5CustomMedia TRAP-TYPE
		ENTERPRISE	netPrinter
		DESCRIPTION
			"The peripheral is utilizing HCI tray 5
			 with Custom Media to process the job 		
			 rather than the tray specified."
	::= 11615

	periphBPLHCITray6CustomMedia TRAP-TYPE
		ENTERPRISE	netPrinter
		DESCRIPTION
			"The peripheral is utilizing HCI tray 6
			 with Custom Media to process the job 		
			 rather than the tray specified."
	::= 11715

	periphBPLHCITray7CustomMedia TRAP-TYPE
		ENTERPRISE	netPrinter
		DESCRIPTION
			"The peripheral is utilizing HCI tray 7
			 with Custom Media to process the job 		
			 rather than the tray specified."
	::= 11815

	periphBPLHCITray8CustomMedia TRAP-TYPE
		ENTERPRISE	netPrinter
		DESCRIPTION
			"The peripheral is utilizing HCI tray 8
			 with Custom Media to process the job 		
			 rather than the tray specified."
	::= 11915

-- Japanese Postcard

	periphBPLMPTrayJapanesePostcard TRAP-TYPE
		ENTERPRISE	netPrinter
		DESCRIPTION
			"The peripheral is utilizing the MP tray or  			 	
			 multipurpose tray1 with Japanese Postcard to 		
			 process the job rather than the tray specified."
	::= 11016

	periphBPLManualFeedJapanesePostcard TRAP-TYPE
		ENTERPRISE	netPrinter
		DESCRIPTION
			"The peripheral is utilizing the manual feed with
 			 Japanese Postcard to process the job rather 
			 than the tray specified."
	::= 11116

	periphBPLPCTrayJapanesePostcard TRAP-TYPE
		ENTERPRISE	netPrinter
		DESCRIPTION
			"The peripheral is utilizing the PC tray, 			 	
			 the upper cassette, or universal tray 2 with
			 Japanese Postcard to process the job rather 
			 than the tray specified."
	::= 11216

	periphBPLLCTrayJapanesePostcard TRAP-TYPE
		ENTERPRISE	netPrinter
		DESCRIPTION
			"The peripheral is utilizing the LC tray, 			 	
			 the lower cassette, or universal tray 3 with
			 Japanese Postcard to process the job rather 
			 than the tray specified."
	::= 11316

	periphBPLEETrayJapanesePostcard TRAP-TYPE
		ENTERPRISE	netPrinter
		DESCRIPTION
			"The peripheral is utilizing the EE tray or
			 envelope feeder with Japanese Postcard to 
			 process the job rather than the tray specified."
	::= 11416

	periphBPLHCITray4JapanesePostcard TRAP-TYPE
		ENTERPRISE	netPrinter
		DESCRIPTION
			"The peripheral is utilizing HCI tray 4
			 with Custom Media to process the job 		
			 rather than the tray specified."
	::= 11516

	periphBPLHCITray5JapanesePostcard TRAP-TYPE
		ENTERPRISE	netPrinter
		DESCRIPTION
			"The peripheral is utilizing HCI tray 5
			 with Japanese Postcard to process the job 		
			 rather than the tray specified."
	::= 11616

	periphBPLHCITray6JapanesePostcard TRAP-TYPE
		ENTERPRISE	netPrinter
		DESCRIPTION
			"The peripheral is utilizing HCI tray 6
			 with Japanese Postcard to process the job 		
			 rather than the tray specified."
	::= 11716

	periphBPLHCITray7JapanesePostcard TRAP-TYPE
		ENTERPRISE	netPrinter
		DESCRIPTION
			"The peripheral is utilizing HCI tray 7
			 with Japanese Postcard to process the job 		
			 rather than the tray specified."
	::= 11816

	periphBPLHCITray8JapanesePostcard TRAP-TYPE
		ENTERPRISE	netPrinter
		DESCRIPTION
			"The peripheral is utilizing HCI tray 8
			 with Japanese Postcard to process the job 		
			 rather than the tray specified."
	::= 11916

-- Japanese Round Trip Postcard

	periphBPLMPTrayJapaneseRTPostcard TRAP-TYPE
		ENTERPRISE	netPrinter
		DESCRIPTION
			"The peripheral is utilizing the MP tray or  			 	
			 multipurpose tray1 with Japanese Round Trip Postcard to 		
			 process the job rather than the tray specified."
	::= 11017

	periphBPLManualFeedJapaneseRTPostcard TRAP-TYPE
		ENTERPRISE	netPrinter
		DESCRIPTION
			"The peripheral is utilizing the manual feed with
 			 Japanese Round Trip Postcard to process the job rather 
			 than the tray specified."
	::= 11117

	periphBPLPCTrayJapaneseRTPostcard TRAP-TYPE
		ENTERPRISE	netPrinter
		DESCRIPTION
			"The peripheral is utilizing the PC tray, 			 	
			 the upper cassette, or universal tray 2 with
			 Japanese Round Trip Postcard to process the job rather 
			 than the tray specified."
	::= 11217

	periphBPLLCTrayJapaneseRTPostcard TRAP-TYPE
		ENTERPRISE	netPrinter
		DESCRIPTION
			"The peripheral is utilizing the LC tray, 			 	
			 the lower cassette, or universal tray 3 with
			 Japanese Round Trip Postcard to process the job rather 
			 than the tray specified."
	::= 11317

	periphBPLEETrayJapaneseRTPostcard TRAP-TYPE
		ENTERPRISE	netPrinter
		DESCRIPTION
			"The peripheral is utilizing the EE tray or
			 envelope feeder with Japanese Round Trip Postcard to 
			 process the job rather than the tray specified."
	::= 11417

	periphBPLHCITray4JapaneseRTPostcard TRAP-TYPE
		ENTERPRISE	netPrinter
		DESCRIPTION
			"The peripheral is utilizing HCI tray 4
			 with Japanese Round Trip Postcard to process the job 		
			 rather than the tray specified."
	::= 11517

	periphBPLHCITray5JapaneseRTPostcard TRAP-TYPE
		ENTERPRISE	netPrinter
		DESCRIPTION
			"The peripheral is utilizing HCI tray 5
			 with Japanese Round Trip Postcard to process the job 		
			 rather than the tray specified."
	::= 11617

	periphBPLHCITray6JapaneseRTPostcard TRAP-TYPE
		ENTERPRISE	netPrinter
		DESCRIPTION
			"The peripheral is utilizing HCI tray 6
			 with Japanese Round Trip Postcard to process the job 		
			 rather than the tray specified."
	::= 11717

	periphBPLHCITray7JapaneseRTPostcard TRAP-TYPE
		ENTERPRISE	netPrinter
		DESCRIPTION
			"The peripheral is utilizing HCI tray 7
			 with Japanese Round Trip Postcard to process the job 		
			 rather than the tray specified."
	::= 11817

	periphBPLHCITray8JapaneseRTPostcard TRAP-TYPE
		ENTERPRISE	netPrinter
		DESCRIPTION
			"The peripheral is utilizing HCI tray 8
			 with Japanese Round Trip Postcard to process the job 		
			 rather than the tray specified."
	::= 11917

-- A5 Paper

	periphBPLMPTrayA5Paper TRAP-TYPE
		ENTERPRISE	netPrinter
		DESCRIPTION
			"The peripheral is utilizing the MP tray or  			 	
			 multipurpose tray1 with A5 paper to 		
			 process the job rather than the tray specified."
	::= 11018

	periphBPLManualFeedA5Paper TRAP-TYPE
		ENTERPRISE	netPrinter
		DESCRIPTION
			"The peripheral is utilizing the manual feed with
 			 A5 paper to process the job rather 
			 than the tray specified."
	::= 11118

	periphBPLPCTrayA5Paper TRAP-TYPE
		ENTERPRISE	netPrinter
		DESCRIPTION
			"The peripheral is utilizing the PC tray, 			 	
			 the upper cassette, or universal tray 2 with
			 A5 paper to process the job rather 
			 than the tray specified."
	::= 11218

	periphBPLLCTrayA5Paper TRAP-TYPE
		ENTERPRISE	netPrinter
		DESCRIPTION
			"The peripheral is utilizing the LC tray, 			 	
			 the lower cassette, or universal tray 3 with
			 A5 paper to process the job rather 
			 than the tray specified."
	::= 11318

	periphBPLEETrayA5Paper TRAP-TYPE
		ENTERPRISE	netPrinter
		DESCRIPTION
			"The peripheral is utilizing the EE tray or
			 envelope feeder with A5 paper to 
			 process the job rather than the tray specified."
	::= 11418

	periphBPLHCITray4A5Paper TRAP-TYPE
		ENTERPRISE	netPrinter
		DESCRIPTION
			"The peripheral is utilizing HCI tray 4
			 with A5 paper to process the job 		
			 rather than the tray specified."
	::= 11518

	periphBPLHCITray5A5Paper TRAP-TYPE
		ENTERPRISE	netPrinter
		DESCRIPTION
			"The peripheral is utilizing HCI tray 5
			 with A5 paper to process the job 		
			 rather than the tray specified."
	::= 11618

	periphBPLHCITray6A5Paper TRAP-TYPE
		ENTERPRISE	netPrinter
		DESCRIPTION
			"The peripheral is utilizing HCI tray 6
			 with A5 paper to process the job 		
			 rather than the tray specified."
	::= 11718

	periphBPLHCITray7A5Paper TRAP-TYPE
		ENTERPRISE	netPrinter
		DESCRIPTION
			"The peripheral is utilizing HCI tray 7
			 with A5 paper to process the job 		
			 rather than the tray specified."
	::= 11818

	periphBPLHCITray8A5Paper TRAP-TYPE
		ENTERPRISE	netPrinter
		DESCRIPTION
			"The peripheral is utilizing HCI tray 8
			 with A5 paper to process the job 		
			 rather than the tray specified."
	::= 11918

-- Letter-R Paper

	periphBPLMPTrayLetterRPaper TRAP-TYPE
		ENTERPRISE	netPrinter
		DESCRIPTION
			"The peripheral is utilizing the MP tray or  			 	
			 multipurpose tray1 with Letter-R Paper to 		
			 process the job rather than the tray specified."
	::= 11019

	periphBPLManualFeedLetterRPaper TRAP-TYPE
		ENTERPRISE	netPrinter
		DESCRIPTION
			"The peripheral is utilizing the manual feed with
 			 Letter-R Paper to process the job rather 
			 than the tray specified."
	::= 11119

	periphBPLPCTrayLetterRPaper TRAP-TYPE
		ENTERPRISE	netPrinter
		DESCRIPTION
			"The peripheral is utilizing the PC tray, 			 	
			 the upper cassette, or universal tray 2 with
			 Letter-R Paper to process the job rather 
			 than the tray specified."
	::= 11219

	periphBPLLCTrayLetterRPaper TRAP-TYPE
		ENTERPRISE	netPrinter
		DESCRIPTION
			"The peripheral is utilizing the LC tray, 			 	
			 the lower cassette, or universal tray 3 with
			 Letter-R Paper to process the job rather 
			 than the tray specified."
	::= 11319

	periphBPLEETrayLetterRPaper TRAP-TYPE
		ENTERPRISE	netPrinter
		DESCRIPTION
			"The peripheral is utilizing the EE tray or
			 envelope feeder with Letter-R Paper to 
			 process the job rather than the tray specified."
	::= 11419

	periphBPLHCITray4LetterRPaper TRAP-TYPE
		ENTERPRISE	netPrinter
		DESCRIPTION
			"The peripheral is utilizing HCI tray 4
			 with Letter-R Paper to process the job 		
			 rather than the tray specified."
	::= 11519

	periphBPLHCITray5LetterRPaper TRAP-TYPE
		ENTERPRISE	netPrinter
		DESCRIPTION
			"The peripheral is utilizing HCI tray 5
			 with Letter-R Paper to process the job 		
			 rather than the tray specified."
	::= 11619

	periphBPLHCITray6LetterRPaper TRAP-TYPE
		ENTERPRISE	netPrinter
		DESCRIPTION
			"The peripheral is utilizing HCI tray 6
			 with Letter-R Paper to process the job 		
			 rather than the tray specified."
	::= 11719

	periphBPLHCITray7LetterRPaper TRAP-TYPE
		ENTERPRISE	netPrinter
		DESCRIPTION
			"The peripheral is utilizing HCI tray 7
			 with Letter-R Paper to process the job 		
			 rather than the tray specified."
	::= 11819

	periphBPLHCITray8LetterRPaper TRAP-TYPE
		ENTERPRISE	netPrinter
		DESCRIPTION
			"The peripheral is utilizing HCI tray 8
			 with Letter-R Paper to process the job 		
			 rather than the tray specified."
	::= 11919

-- A4-R Paper

	periphBPLMPTrayA4RPaper TRAP-TYPE
		ENTERPRISE	netPrinter
		DESCRIPTION
			"The peripheral is utilizing the MP tray or  			 	
			 multipurpose tray1 with A4-R Paper to 		
			 process the job rather than the tray specified."
	::= 11020

	periphBPLManualFeedA4RPaper TRAP-TYPE
		ENTERPRISE	netPrinter
		DESCRIPTION
			"The peripheral is utilizing the manual feed with
 			 A4-R Paper to process the job rather 
			 than the tray specified."
	::= 11120

	periphBPLPCTrayA4RPaper TRAP-TYPE
		ENTERPRISE	netPrinter
		DESCRIPTION
			"The peripheral is utilizing the PC tray, 			 	
			 the upper cassette, or universal tray 2 with
			 A4-R Paper to process the job rather 
			 than the tray specified."
	::= 11220

	periphBPLLCTrayA4RPaper TRAP-TYPE
		ENTERPRISE	netPrinter
		DESCRIPTION
			"The peripheral is utilizing the LC tray, 			 	
			 the lower cassette, or universal tray 3 with
			 A4-R Paper to process the job rather 
			 than the tray specified."
	::= 113120

	periphBPLEETrayA4RPaper TRAP-TYPE
		ENTERPRISE	netPrinter
		DESCRIPTION
			"The peripheral is utilizing the EE tray or
			 envelope feeder with A4-R Paper to 
			 process the job rather than the tray specified."
	::= 11420

	periphBPLHCITray4A4RPaper TRAP-TYPE
		ENTERPRISE	netPrinter
		DESCRIPTION
			"The peripheral is utilizing HCI tray 4
			 with A4-R Paper to process the job 		
			 rather than the tray specified."
	::= 11520

	periphBPLHCITray5A4RPaper TRAP-TYPE
		ENTERPRISE	netPrinter
		DESCRIPTION
			"The peripheral is utilizing HCI tray 5
			 with A4-R Paper to process the job 		
			 rather than the tray specified."
	::= 11620

	periphBPLHCITray6A4RPaper TRAP-TYPE
		ENTERPRISE	netPrinter
		DESCRIPTION
			"The peripheral is utilizing HCI tray 6
			 with A4-R Paper to process the job 		
			 rather than the tray specified."
	::= 11720

	periphBPLHCITray7A4RPaper TRAP-TYPE
		ENTERPRISE	netPrinter
		DESCRIPTION
			"The peripheral is utilizing HCI tray 7
			 with A4-R Paper to process the job 		
			 rather than the tray specified."
	::= 11820

	periphBPLHCITray8A4RPaper TRAP-TYPE
		ENTERPRISE	netPrinter
		DESCRIPTION
			"The peripheral is utilizing HCI tray 8
			 with A4-R Paper to process the job 		
			 rather than the tray specified."
	::= 11920

-- A5-R Paper

	periphBPLMPTrayA5RPaper TRAP-TYPE
		ENTERPRISE	netPrinter
		DESCRIPTION
			"The peripheral is utilizing the MP tray or  			 	
			 multipurpose tray1 with A5-R Paper to 		
			 process the job rather than the tray specified."
	::= 11021

	periphBPLManualFeedA5RPaper TRAP-TYPE
		ENTERPRISE	netPrinter
		DESCRIPTION
			"The peripheral is utilizing the manual feed with
 			 A5-R Paper to process the job rather 
			 than the tray specified."
	::= 11121

	periphBPLPCTrayA5RPaper TRAP-TYPE
		ENTERPRISE	netPrinter
		DESCRIPTION
			"The peripheral is utilizing the PC tray, 			 	
			 the upper cassette, or universal tray 2 with
			 A5-R Paper to process the job rather 
			 than the tray specified."
	::= 11221

	periphBPLLCTrayA5RPaper TRAP-TYPE
		ENTERPRISE	netPrinter
		DESCRIPTION
			"The peripheral is utilizing the LC tray, 			 	
			 the lower cassette, or universal tray 3 with
			 A5-R Paper to process the job rather 
			 than the tray specified."
	::= 11321

	periphBPLEETrayA5RPaper TRAP-TYPE
		ENTERPRISE	netPrinter
		DESCRIPTION
			"The peripheral is utilizing the EE tray or
			 envelope feeder with A5-R Paper to 
			 process the job rather than the tray specified."
	::= 11421

	periphBPLHCITray4A5RPaper TRAP-TYPE
		ENTERPRISE	netPrinter
		DESCRIPTION
			"The peripheral is utilizing HCI tray 4
			 with A5-R Paper to process the job 		
			 rather than the tray specified."
	::= 11521

	periphBPLHCITray5A5RPaper TRAP-TYPE
		ENTERPRISE	netPrinter
		DESCRIPTION
			"The peripheral is utilizing HCI tray 5
			 with A5-R Paper to process the job 		
			 rather than the tray specified."
	::= 11621

	periphBPLHCITray6A5RPaper TRAP-TYPE
		ENTERPRISE	netPrinter
		DESCRIPTION
			"The peripheral is utilizing HCI tray 6
			 with A5-R Paper to process the job 		
			 rather than the tray specified."
	::= 11721

	periphBPLHCITray7A5RPaper TRAP-TYPE
		ENTERPRISE	netPrinter
		DESCRIPTION
			"The peripheral is utilizing HCI tray 7
			 with A5-R Paper to process the job 		
			 rather than the tray specified."
	::= 11821

	periphBPLHCITray8A5RPaper TRAP-TYPE
		ENTERPRISE	netPrinter
		DESCRIPTION
			"The peripheral is utilizing HCI tray 8
			 with A5-R Paper to process the job 		
			 rather than the tray specified."
	::= 11921

-- Japan B5-R Paper

	periphBPLMPTrayJapanB5RPaper TRAP-TYPE
		ENTERPRISE	netPrinter
		DESCRIPTION
			"The peripheral is utilizing the MP tray or  			 	
			 multipurpose tray1 with Japan B5-R Paper to 		
			 process the job rather than the tray specified."
	::= 11022

	periphBPLManualFeedJapanB5RPaper TRAP-TYPE
		ENTERPRISE	netPrinter
		DESCRIPTION
			"The peripheral is utilizing the manual feed with
 			 Japan B5-R Paper to process the job rather 
			 than the tray specified."
	::= 11122

	periphBPLPCTrayJapanB5RPaper TRAP-TYPE
		ENTERPRISE	netPrinter
		DESCRIPTION
			"The peripheral is utilizing the PC tray, 			 	
			 the upper cassette, or universal tray 2 with
			 Japan B5-R Paper to process the job rather 
			 than the tray specified."
	::= 11222

	periphBPLLCTrayJapanB5RPaper TRAP-TYPE
		ENTERPRISE	netPrinter
		DESCRIPTION
			"The peripheral is utilizing the LC tray, 			 	
			 the lower cassette, or universal tray 3 with
			 Japan B5-R Paper to process the job rather 
			 than the tray specified."
	::= 11322

	periphBPLEETrayJapanB5RPaper TRAP-TYPE
		ENTERPRISE	netPrinter
		DESCRIPTION
			"The peripheral is utilizing the EE tray or
			 envelope feeder with Japan B5-R Paper to 
			 process the job rather than the tray specified."
	::= 11422

	periphBPLHCITray4JapanB5RPaper TRAP-TYPE
		ENTERPRISE	netPrinter
		DESCRIPTION
			"The peripheral is utilizing HCI tray 4
			 with Japan B5-R Paper to process the job 		
			 rather than the tray specified."
	::= 11522

	periphBPLHCITray5JapanB5RPaper TRAP-TYPE
		ENTERPRISE	netPrinter
		DESCRIPTION
			"The peripheral is utilizing HCI tray 5
			 with Japan B5-R Paper to process the job 		
			 rather than the tray specified."
	::= 11622

	periphBPLHCITray6JapanB5RPaper TRAP-TYPE
		ENTERPRISE	netPrinter
		DESCRIPTION
			"The peripheral is utilizing HCI tray 6
			 with Japan B5-R Paper to process the job 		
			 rather than the tray specified."
	::= 11722

	periphBPLHCITray7JapanB5RPaper TRAP-TYPE
		ENTERPRISE	netPrinter
		DESCRIPTION
			"The peripheral is utilizing HCI tray 7
			 with Japan B5-R Paper to process the job 		
			 rather than the tray specified."
	::= 11822

	periphBPLHCITray8JapanB5RPaper TRAP-TYPE
		ENTERPRISE	netPrinter
		DESCRIPTION
			"The peripheral is utilizing HCI tray 8
			 with Japan B5-R Paper to process the job 		
			 rather than the tray specified."
	::= 11922

-- Exec-R Paper

	periphBPLMPTrayExecRPaper TRAP-TYPE
		ENTERPRISE	netPrinter
		DESCRIPTION
			"The peripheral is utilizing the MP tray or  			 	
			 multipurpose tray1 with Exec-R Paper to 		
			 process the job rather than the tray specified."
	::= 11023

	periphBPLManualFeedExecRPaper TRAP-TYPE
		ENTERPRISE	netPrinter
		DESCRIPTION
			"The peripheral is utilizing the manual feed with
 			 Exec-R Paper to process the job rather 
			 than the tray specified."
	::= 11123

	periphBPLPCTrayExecRPaper TRAP-TYPE
		ENTERPRISE	netPrinter
		DESCRIPTION
			"The peripheral is utilizing the PC tray, 			 	
			 the upper cassette, or universal tray 2 with
			 Exec-R Paper to process the job rather 
			 than the tray specified."
	::= 11223

	periphBPLLCTrayExecRPaper TRAP-TYPE
		ENTERPRISE	netPrinter
		DESCRIPTION
			"The peripheral is utilizing the LC tray, 			 	
			 the lower cassette, or universal tray 3 with
			 Exec-R Paper to process the job rather 
			 than the tray specified."
	::= 11323

	periphBPLEETrayExecRPaper TRAP-TYPE
		ENTERPRISE	netPrinter
		DESCRIPTION
			"The peripheral is utilizing the EE tray or
			 envelope feeder with Exec-R Paper to 
			 process the job rather than the tray specified."
	::= 11423

	periphBPLHCITray4ExecRPaper TRAP-TYPE
		ENTERPRISE	netPrinter
		DESCRIPTION
			"The peripheral is utilizing HCI tray 4
			 with Exec-R Paper to process the job 		
			 rather than the tray specified."
	::= 11523

	periphBPLHCITray5ExecRPaper TRAP-TYPE
		ENTERPRISE	netPrinter
		DESCRIPTION
			"The peripheral is utilizing HCI tray 5
			 with Exec-R Paper to process the job 		
			 rather than the tray specified."
	::= 11623

	periphBPLHCITray6ExecRPaper TRAP-TYPE
		ENTERPRISE	netPrinter
		DESCRIPTION
			"The peripheral is utilizing HCI tray 6
			 with Exec-R Paper to process the job 		
			 rather than the tray specified."
	::= 11723

	periphBPLHCITray7ExecRPaper TRAP-TYPE
		ENTERPRISE	netPrinter
		DESCRIPTION
			"The peripheral is utilizing HCI tray 7
			 with Exec-R Paper to process the job 		
			 rather than the tray specified."
	::= 11823

	periphBPLHCITray8ExecRPaper TRAP-TYPE
		ENTERPRISE	netPrinter
		DESCRIPTION
			"The peripheral is utilizing HCI tray 8
			 with Exec-R Paper to process the job 		
			 rather than the tray specified."
	::= 11923

-- A6 Paper

	periphBPLMPTrayA6Paper TRAP-TYPE
		ENTERPRISE	netPrinter
		DESCRIPTION
			"The peripheral is utilizing the MP tray or  			 	
			 multipurpose tray1 with A6 Paper to 		
			 process the job rather than the tray specified."
	::= 11024

	periphBPLManualFeedA6Paper TRAP-TYPE
		ENTERPRISE	netPrinter
		DESCRIPTION
			"The peripheral is utilizing the manual feed with
 			 A6 Paper to process the job rather 
			 than the tray specified."
	::= 11124

	periphBPLPCTrayA6Paper TRAP-TYPE
		ENTERPRISE	netPrinter
		DESCRIPTION
			"The peripheral is utilizing the PC tray, 			 	
			 the upper cassette, or universal tray 2 with
			 A6 Paper to process the job rather 
			 than the tray specified."
	::= 11224

	periphBPLLCTrayA6Paper TRAP-TYPE
		ENTERPRISE	netPrinter
		DESCRIPTION
			"The peripheral is utilizing the LC tray, 			 	
			 the lower cassette, or universal tray 3 with
			 A6 Paper to process the job rather 
			 than the tray specified."
	::= 11324

	periphBPLEETrayA6Paper TRAP-TYPE
		ENTERPRISE	netPrinter
		DESCRIPTION
			"The peripheral is utilizing the EE tray or
			 envelope feeder with A6 Paper to 
			 process the job rather than the tray specified."
	::= 11424

	periphBPLHCITray4A6Paper TRAP-TYPE
		ENTERPRISE	netPrinter
		DESCRIPTION
			"The peripheral is utilizing HCI tray 4
			 with A6 Paper to process the job 		
			 rather than the tray specified."
	::= 11524

	periphBPLHCITray5A6Paper TRAP-TYPE
		ENTERPRISE	netPrinter
		DESCRIPTION
			"The peripheral is utilizing HCI tray 5
			 with A6 Paper to process the job 		
			 rather than the tray specified."
	::= 11624

	periphBPLHCITray6A6Paper TRAP-TYPE
		ENTERPRISE	netPrinter
		DESCRIPTION
			"The peripheral is utilizing HCI tray 6
			 with A6 Paper to process the job 		
			 rather than the tray specified."
	::= 11724

	periphBPLHCITray7A6Paper TRAP-TYPE
		ENTERPRISE	netPrinter
		DESCRIPTION
			"The peripheral is utilizing HCI tray 7
			 with A6 Paper to process the job 		
			 rather than the tray specified."
	::= 11824

	periphBPLHCITray8A6Paper TRAP-TYPE
		ENTERPRISE	netPrinter
		DESCRIPTION
			"The peripheral is utilizing HCI tray 8
			 with A6 Paper to process the job 		
			 rather than the tray specified."
	::= 11924


-- Foolscap Paper

	periphBPLMPTrayFoolscapPaper TRAP-TYPE
		ENTERPRISE	netPrinter
		DESCRIPTION
			"The peripheral is utilizing the MP tray or  			 	
			 multipurpose tray1 with Foolscap Paper to 		
			 process the job rather than the tray specified."
	::= 11025

	periphBPLManualFeedFoolscapPaper TRAP-TYPE
		ENTERPRISE	netPrinter
		DESCRIPTION
			"The peripheral is utilizing the manual feed with
 			 Foolscap Paper to process the job rather 
			 than the tray specified."
	::= 11125

	periphBPLPCTrayFoolscapPaper TRAP-TYPE
		ENTERPRISE	netPrinter
		DESCRIPTION
			"The peripheral is utilizing the PC tray, 			 	
			 the upper cassette, or universal tray 2 with
			 Foolscap Paper to process the job rather 
			 than the tray specified."
	::= 11225

	periphBPLLCTrayFoolscapPaper TRAP-TYPE
		ENTERPRISE	netPrinter
		DESCRIPTION
			"The peripheral is utilizing the LC tray, 			 	
			 the lower cassette, or universal tray 3 with
			 Foolscap Paper to process the job rather 
			 than the tray specified."
	::= 11325

	periphBPLEETrayFoolscapPaper TRAP-TYPE
		ENTERPRISE	netPrinter
		DESCRIPTION
			"The peripheral is utilizing the EE tray or
			 envelope feeder with Foolscap Paper to 
			 process the job rather than the tray specified."
	::= 11425

	periphBPLHCITray4FoolscapPaper TRAP-TYPE
		ENTERPRISE	netPrinter
		DESCRIPTION
			"The peripheral is utilizing HCI tray 4
			 with Foolscap Paper to process the job 		
			 rather than the tray specified."
	::= 11525

	periphBPLHCITray5FoolscapPaper TRAP-TYPE
		ENTERPRISE	netPrinter
		DESCRIPTION
			"The peripheral is utilizing HCI tray 5
			 with Foolscap Paper to process the job 		
			 rather than the tray specified."
	::= 11625

	periphBPLHCITray6FoolscapPaper TRAP-TYPE
		ENTERPRISE	netPrinter
		DESCRIPTION
			"The peripheral is utilizing HCI tray 6
			 with Foolscap Paper to process the job 		
			 rather than the tray specified."
	::= 11725

	periphBPLHCITray7FoolscapPaper TRAP-TYPE
		ENTERPRISE	netPrinter
		DESCRIPTION
			"The peripheral is utilizing HCI tray 7
			 with Foolscap Paper to process the job 		
			 rather than the tray specified."
	::= 11825

	periphBPLHCITray8FoolscapPaper TRAP-TYPE
		ENTERPRISE	netPrinter
		DESCRIPTION
			"The peripheral is utilizing HCI tray 8
			 with Foolscap Paper to process the job 		
			 rather than the tray specified."
	::= 11925

-- Japan B6 Paper

	periphBPLMPTrayJapanB6Paper TRAP-TYPE
		ENTERPRISE	netPrinter
		DESCRIPTION
			"The peripheral is utilizing the MP tray or  			 	
			 multipurpose tray1 with Japan-B6 Paper to 		
			 process the job rather than the tray specified."
	::= 11026

	periphBPLManualFeedJapanB6Paper TRAP-TYPE
		ENTERPRISE	netPrinter
		DESCRIPTION
			"The peripheral is utilizing the manual feed with
 			 Japan-B6 Paper to process the job rather 
			 than the tray specified."
	::= 11126

	periphBPLPCTrayJapanB6Paper TRAP-TYPE
		ENTERPRISE	netPrinter
		DESCRIPTION
			"The peripheral is utilizing the PC tray, 			 	
			 the upper cassette, or universal tray 2 with
			 Japan-B6 Paper to process the job rather 
			 than the tray specified."
	::= 11226

	periphBPLLCTrayJapanB6Paper TRAP-TYPE
		ENTERPRISE	netPrinter
		DESCRIPTION
			"The peripheral is utilizing the LC tray, 			 	
			 the lower cassette, or universal tray 3 with
			 Japan-B6 Paper to process the job rather 
			 than the tray specified."
	::= 11326

	periphBPLEETrayJapanB6Paper TRAP-TYPE
		ENTERPRISE	netPrinter
		DESCRIPTION
			"The peripheral is utilizing the EE tray or
			 envelope feeder with Japan-B6 Paper to 
			 process the job rather than the tray specified."
	::= 11426

	periphBPLHCITray4JapanB6Paper TRAP-TYPE
		ENTERPRISE	netPrinter
		DESCRIPTION
			"The peripheral is utilizing HCI tray 4
			 with Japan-B6 Paper to process the job 		
			 rather than the tray specified."
	::= 11526

	periphBPLHCITray5JapanB6Paper TRAP-TYPE
		ENTERPRISE	netPrinter
		DESCRIPTION
			"The peripheral is utilizing HCI tray 5
			 with Japan-B6 Paper to process the job 		
			 rather than the tray specified."
	::= 11626

	periphBPLHCITray6JapanB6Paper TRAP-TYPE
		ENTERPRISE	netPrinter
		DESCRIPTION
			"The peripheral is utilizing HCI tray 6
			 with Japan-B6 Paper to process the job 		
			 rather than the tray specified."
	::= 11726

	periphBPLHCITray7JapanB6Paper TRAP-TYPE
		ENTERPRISE	netPrinter
		DESCRIPTION
			"The peripheral is utilizing HCI tray 7
			 with Japan-B6 Paper to process the job 		
			 rather than the tray specified."
	::= 11826

	periphBPLHCITray8JapanB6Paper TRAP-TYPE
		ENTERPRISE	netPrinter
		DESCRIPTION
			"The peripheral is utilizing HCI tray 8
			 with Japan-B6 Paper to process the job 		
			 rather than the tray specified."
	::= 11926






-- Background paper status messages (BPS) - these messages appear when a 
-- paper input source is loading or lifting.

-- Tray Open

	periphBPSMPTrayOpen TRAP-TYPE
		ENTERPRISE	netPrinter
		DESCRIPTION
			"The peripheral has detected that the MP tray or 
 		 	 multi-purpose tray 1 is Open."
	::= 12001

	periphBPSManualFeedOpen TRAP-TYPE
		ENTERPRISE	netPrinter
		DESCRIPTION
			"The peripheral has detected that the Manual Feed tray is Open."
	::= 12101

	periphBPSTray2Open TRAP-TYPE
		ENTERPRISE	netPrinter
		DESCRIPTION
			"The peripheral has detected that the PC tray, upper cassette
			 or universal tray 2 is Open."
	::= 12201

	periphBPSTray3Open TRAP-TYPE
		ENTERPRISE	netPrinter
		DESCRIPTION
			"The peripheral has detected that the LC tray, lower cassette,
			 or universal tray 3 is Open."
	::= 12301

	periphBPSEnvelopeTrayOpen TRAP-TYPE
		ENTERPRISE	netPrinter
		DESCRIPTION
			"The peripheral has detected that the EE tray or 
			 envelope feeder is Open."
	::= 12401

	periphBPSHCITray4Open TRAP-TYPE
		ENTERPRISE	netPrinter
		DESCRIPTION
			"The peripheral has detected that any tray 4 is Open."
	::= 12501

	periphBPSHCITray5Open TRAP-TYPE
		ENTERPRISE	netPrinter
		DESCRIPTION
			"The peripheral has detected that any tray 5 is Open."
	::= 12601

	periphBPSHCITray6Open TRAP-TYPE
		ENTERPRISE	netPrinter
		DESCRIPTION
			"The peripheral has detected that any tray 6 is Open."
	::= 12701

	periphBPSHCITray7Open TRAP-TYPE
		ENTERPRISE	netPrinter
		DESCRIPTION
			"The peripheral has detected that any tray 7 is Open."
	::= 12801

	periphBPSHCITray8Open TRAP-TYPE
		ENTERPRISE	netPrinter
		DESCRIPTION
			"The peripheral has detected that any tray 7 is Open."
	::= 12901

-- Tray Lifting

	periphBPSTrayLifting TRAP-TYPE
		ENTERPRISE	netPrinter
		DESCRIPTION
			"The peripheral has detected that the MP tray or 
 		 	 multi-purpose tray 1 is lifting."
	::= 12002

	periphBPSManualFeedLifting TRAP-TYPE
		ENTERPRISE	netPrinter
		DESCRIPTION
			"The peripheral has detected that the Manual Feed tray is lifting."
	::= 12102

	periphBPSTray2Lifting TRAP-TYPE
		ENTERPRISE	netPrinter
		DESCRIPTION
			"The peripheral has detected that the PC tray, upper cassette
			 or universal tray 2 is lifting."
	::= 12202

	periphBPSTray3Lifting TRAP-TYPE
		ENTERPRISE	netPrinter
		DESCRIPTION
			"The peripheral has detected that the LC tray, lower cassette,
			 or universal tray 3 is lifting."
	::= 12302

	periphBPSEnvelopeTrayLifting TRAP-TYPE
		ENTERPRISE	netPrinter
		DESCRIPTION
			"The peripheral has detected that the EE tray or 
			 envelope feeder is lifting."
	::= 12402

	periphBPSHCITray4Lifting TRAP-TYPE
		ENTERPRISE	netPrinter
		DESCRIPTION
			"The peripheral has detected that any tray 4 is lifting."
	::= 12502

	periphBPSHCITray5Lifting TRAP-TYPE
		ENTERPRISE	netPrinter
		DESCRIPTION
			"The peripheral has detected that any tray 5 is lifting."
	::= 12602

	periphBPSHCITray6Lifting TRAP-TYPE
		ENTERPRISE	netPrinter
		DESCRIPTION
			"The peripheral has detected that any tray 6 is lifting."
	::= 12702

	periphBPSHCITray7Lifting TRAP-TYPE
		ENTERPRISE	netPrinter
		DESCRIPTION
			"The peripheral has detected that any tray 7 is lifting."
	::= 12802

	periphBPSHCITray8Lifting TRAP-TYPE
		ENTERPRISE	netPrinter
		DESCRIPTION
			"The peripheral has detected that any tray 8 is lifting."
	::= 12902


-- Output Bin Full messages

	periphOBSFaceDownBinFull TRAP-TYPE
		ENTERPRISE	netPrinter
		DESCRIPTION
			"The peripheral has detected that face down output bin is full."
	::= 15001

	periphOBSFaceUpBinFull TRAP-TYPE
		ENTERPRISE	netPrinter
		DESCRIPTION
			"The peripheral has detected that face up output bin is full."
	::= 15011

	periphOutputBinFirstFull TRAP-TYPE
		ENTERPRISE	netPrinter
		DESCRIPTION
			"The peripheral has detected that the first Output Bin is full."
	::= 15021

	periphOBSNumber03Full TRAP-TYPE
		ENTERPRISE	netPrinter
		DESCRIPTION
			"The peripheral has detected that Output Bin 03 is full."
	::= 15031

	periphOBSNumber04Full TRAP-TYPE
		ENTERPRISE	netPrinter
		DESCRIPTION
			"The peripheral has detected that Output Bin 04 is full."
	::= 15041

	periphOBSNumber05Full TRAP-TYPE
		ENTERPRISE	netPrinter
		DESCRIPTION
			"The peripheral has detected that Output Bin 05 is full."
	::= 15051

	periphOBSNumber06Full TRAP-TYPE
		ENTERPRISE	netPrinter
		DESCRIPTION
			"The peripheral has detected that Output Bin 06 is full."
	::= 15061

	periphOBSNumber07Full TRAP-TYPE
		ENTERPRISE	netPrinter
		DESCRIPTION
			"The peripheral has detected that Output Bin 07 is full."
	::= 15071

	periphOBSNumber08Full TRAP-TYPE
		ENTERPRISE	netPrinter
		DESCRIPTION
			"The peripheral has detected that Output Bin 08 is full."
	::= 15081

	periphOBSNumber09Full TRAP-TYPE
		ENTERPRISE	netPrinter
		DESCRIPTION
			"The peripheral has detected that Output Bin 09 is full."
	::= 15091

	periphOBSNumber10Full TRAP-TYPE
		ENTERPRISE	netPrinter
		DESCRIPTION
			"The peripheral has detected that Output Bin 10 is full."
	::= 15101

	periphOBSNumber11Full TRAP-TYPE
		ENTERPRISE	netPrinter
		DESCRIPTION
			"The peripheral has detected that Output Bin 11 is full."
	::= 15111

	periphOBSNumber12Full TRAP-TYPE
		ENTERPRISE	netPrinter
		DESCRIPTION
			"The peripheral has detected that Output Bin 12 is full."
	::= 15121

	periphOBSNumber13Full TRAP-TYPE
		ENTERPRISE	netPrinter
		DESCRIPTION
			"The peripheral has detected that Output Bin 13 is full."
	::= 15131

	periphOBSNumber14Full TRAP-TYPE
		ENTERPRISE	netPrinter
		DESCRIPTION
			"The peripheral has detected that Output Bin 14 is full."
	::= 15141

	periphOBSNumber15Full TRAP-TYPE
		ENTERPRISE	netPrinter
		DESCRIPTION
			"The peripheral has detected that Output Bin 15 is full."
	::= 15151

-- Output Bin Open messages

	periphOBSFaceDownBinOpen TRAP-TYPE
		ENTERPRISE	netPrinter
		DESCRIPTION
			"The peripheral has detected that face down output bin is Open."
	::= 15002

	periphOBSFaceUpBinOpen TRAP-TYPE
		ENTERPRISE	netPrinter
		DESCRIPTION
			"The peripheral has detected that face up output bin is Open."
	::= 15012

	periphOutputBinFirstOpen TRAP-TYPE
		ENTERPRISE	netPrinter
		DESCRIPTION
			"The peripheral has detected that the first Output Bin is Open."
	::= 15022

	periphOBSNumber03Open TRAP-TYPE
		ENTERPRISE	netPrinter
		DESCRIPTION
			"The peripheral has detected that Output Bin 03 is Open."
	::= 15032

	periphOBSNumber04Open TRAP-TYPE
		ENTERPRISE	netPrinter
		DESCRIPTION
			"The peripheral has detected that Output Bin 04 is Open."
	::= 15042

	periphOBSNumber05Open TRAP-TYPE
		ENTERPRISE	netPrinter
		DESCRIPTION
			"The peripheral has detected that Output Bin 05 is Open."
	::= 15052

	periphOBSNumber06Open TRAP-TYPE
		ENTERPRISE	netPrinter
		DESCRIPTION
			"The peripheral has detected that Output Bin 06 is Open."
	::= 15062

	periphOBSNumber07Open TRAP-TYPE
		ENTERPRISE	netPrinter
		DESCRIPTION
			"The peripheral has detected that Output Bin 07 is Open."
	::= 15072

	periphOBSNumber08Open TRAP-TYPE
		ENTERPRISE	netPrinter
		DESCRIPTION
			"The peripheral has detected that Output Bin 08 is Open."
	::= 15082

	periphOBSNumber09Open TRAP-TYPE
		ENTERPRISE	netPrinter
		DESCRIPTION
			"The peripheral has detected that Output Bin 09 is Open."
	::= 15092

	periphOBSNumber10Open TRAP-TYPE
		ENTERPRISE	netPrinter
		DESCRIPTION
			"The peripheral has detected that Output Bin 10 is Open."
	::= 15102

	periphOBSNumber11Open TRAP-TYPE
		ENTERPRISE	netPrinter
		DESCRIPTION
			"The peripheral has detected that Output Bin 11 is Open."
	::= 15112

	periphOBSNumber12Open TRAP-TYPE
		ENTERPRISE	netPrinter
		DESCRIPTION
			"The peripheral has detected that Output Bin 12 is Open."
	::= 15122

	periphOBSNumber13Open TRAP-TYPE
		ENTERPRISE	netPrinter
		DESCRIPTION
			"The peripheral has detected that Output Bin 13 is Open."
	::= 15132

	periphOBSNumber14Open TRAP-TYPE
		ENTERPRISE	netPrinter
		DESCRIPTION
			"The peripheral has detected that Output Bin 14 is Open."
	::= 15142

	periphOBSNumber15Open TRAP-TYPE
		ENTERPRISE	netPrinter
		DESCRIPTION
			"The peripheral has detected that Output Bin 15 is Open."
	::= 15152

-- Output Bin Broken messages

	periphOBSFaceDownBinBroken TRAP-TYPE
		ENTERPRISE	netPrinter
		DESCRIPTION
			"The peripheral has detected that face down output bin is Broken."
	::= 15003

	periphOBSFaceUpBinBroken TRAP-TYPE
		ENTERPRISE	netPrinter
		DESCRIPTION
			"The peripheral has detected that face up output bin is Broken."
	::= 15013

	periphOutputBinFirstBroken TRAP-TYPE
		ENTERPRISE	netPrinter
		DESCRIPTION
			"The peripheral has detected that the first Output Bin is Broken."
	::= 15023

	periphOBSNumber03Broken TRAP-TYPE
		ENTERPRISE	netPrinter
		DESCRIPTION
			"The peripheral has detected that Output Bin 03 is Broken."
	::= 15033

	periphOBSNumber04Broken TRAP-TYPE
		ENTERPRISE	netPrinter
		DESCRIPTION
			"The peripheral has detected that Output Bin 04 is Broken."
	::= 15043

	periphOBSNumber05Broken TRAP-TYPE
		ENTERPRISE	netPrinter
		DESCRIPTION
			"The peripheral has detected that Output Bin 05 is Broken."
	::= 15053

	periphOBSNumber06Broken TRAP-TYPE
		ENTERPRISE	netPrinter
		DESCRIPTION
			"The peripheral has detected that Output Bin 06 is Broken."
	::= 15063

	periphOBSNumber07Broken TRAP-TYPE
		ENTERPRISE	netPrinter
		DESCRIPTION
			"The peripheral has detected that Output Bin 07 is Broken."
	::= 15073

	periphOBSNumber08Broken TRAP-TYPE
		ENTERPRISE	netPrinter
		DESCRIPTION
			"The peripheral has detected that Output Bin 08 is Broken."
	::= 15083

	periphOBSNumber09Broken TRAP-TYPE
		ENTERPRISE	netPrinter
		DESCRIPTION
			"The peripheral has detected that Output Bin 09 is Broken."
	::= 15093

	periphOBSNumber10Broken TRAP-TYPE
		ENTERPRISE	netPrinter
		DESCRIPTION
			"The peripheral has detected that Output Bin 10 is Broken."
	::= 15103

	periphOBSNumber11Broken TRAP-TYPE
		ENTERPRISE	netPrinter
		DESCRIPTION
			"The peripheral has detected that Output Bin 11 is Broken."
	::= 15113

	periphOBSNumber12Broken TRAP-TYPE
		ENTERPRISE	netPrinter
		DESCRIPTION
			"The peripheral has detected that Output Bin 12 is Broken."
	::= 15123

	periphOBSNumber13Broken TRAP-TYPE
		ENTERPRISE	netPrinter
		DESCRIPTION
			"The peripheral has detected that Output Bin 13 is Broken."
	::= 15133

	periphOBSNumber14Broken TRAP-TYPE
		ENTERPRISE	netPrinter
		DESCRIPTION
			"The peripheral has detected that Output Bin 14 is Broken."
	::= 15143

	periphOBSNumber15Broken TRAP-TYPE
		ENTERPRISE	netPrinter
		DESCRIPTION
			"The peripheral has detected that Output Bin 15 is Broken."
	::= 15153



-- PJL Parser Errors - the entire PJl command was ignored


	periphPJLPEGenericSyntax TRAP-TYPE
		ENTERPRISE	netPrinter
		DESCRIPTION
			"PJL parser encountered a generic syntax error and 
		 	 ignored the PJL command."
	::= 20001


	periphPJLPEUnsupportedCommand TRAP-TYPE
		ENTERPRISE	netPrinter
		DESCRIPTION
			"PJL parser encountered an unsupported command and 
		 	 ignored the PJL command."
	::= 20002

	periphPJLPEUnsupportedEntity TRAP-TYPE
		ENTERPRISE	netPrinter
		DESCRIPTION
			"PJL parser encountered a referral to an unsupported
			 personality, system, or I/O port."
	::= 20004


	periphPJLPECommandBufferOverflow TRAP-TYPE
		ENTERPRISE	netPrinter
		DESCRIPTION
			"PJL command buffer was exceeded."
	::= 20005


	periphPJLPEIllegalCharacter TRAP-TYPE
		ENTERPRISE	netPrinter
		DESCRIPTION
			"PJL parser encountered an illegal character."
	::= 20006


	periphPJLPEMissingCharacter TRAP-TYPE
		ENTERPRISE	netPrinter
		DESCRIPTION
			"PJL parser did not encounter the expected <WS>
			 or [<CR>] <LF> after closing quotes."
	::= 20007

	periphPJLPEInvalidCharacter1 TRAP-TYPE
		ENTERPRISE	netPrinter
		DESCRIPTION
			"PJL parser encountered an invalid character 
			 in an alphanumeric value."
	::= 20008

	periphPJLPEInvalidCharacter2 TRAP-TYPE
		ENTERPRISE	netPrinter
		DESCRIPTION
			"PJL parser encountered an invalid character 
			 in a numeric value."
	::= 20009

	periphPJLPEInvalidCharacter3 TRAP-TYPE
		ENTERPRISE	netPrinter
		DESCRIPTION
			"PJL parser encountered an invalid character 
			 at the start of a string, alphanumberic value,
			 or numeric value."
	::= 20010


	periphPJLPESyntaxError1 TRAP-TYPE
		ENTERPRISE	netPrinter
		DESCRIPTION
			"PJL parser encountered a string missing the 
			 closing double-quote character."
	::= 20011

	periphPJLPESyntaxError2 TRAP-TYPE
		ENTERPRISE	netPrinter
		DESCRIPTION
			"PJL parser encountered a numeric value starting
			 with a decimal point."
	::= 20012

	periphPJLPESyntaxError3 TRAP-TYPE
		ENTERPRISE	netPrinter
		DESCRIPTION
			"PJL parser encountered a numeric value without
			 any digits."
	::= 20013

	periphPJLPESyntaxError4 TRAP-TYPE
		ENTERPRISE	netPrinter
		DESCRIPTION
			"PJL parser encountered no alphanumeric value
			 after command modifier."
	::= 20014

	periphPJLPESyntaxError5 TRAP-TYPE
		ENTERPRISE	netPrinter
		DESCRIPTION
			"PJL parser encountered the option name and equal
			 sign, but no value field."
	::= 20015

	periphPJLPESyntaxError6 TRAP-TYPE
		ENTERPRISE	netPrinter
		DESCRIPTION
			"PJL parser encountered more than one command 
			 modifier."
	::= 20016

	periphPJLPESyntaxError7 TRAP-TYPE
		ENTERPRISE	netPrinter
		DESCRIPTION
			"PJL parser encountered a command modifier
			 after an option rather than preceding it."
	::= 20017

	periphPJLPESyntaxError8 TRAP-TYPE
		ENTERPRISE	netPrinter
		DESCRIPTION
			"PJL parser encountered a command not an 
			 alphanumeric value."
	::= 20018

	periphPJLPESyntaxError9 TRAP-TYPE
		ENTERPRISE	netPrinter
		DESCRIPTION
			"PJL parser encountered a numeric value when 
			 it expected an alphanumeric value."
	::= 20019

	periphPJLPESyntaxError10 TRAP-TYPE
		ENTERPRISE	netPrinter
		DESCRIPTION
			"PJL parser encountered a string when 
			 it expected an alphanumeric value."
	::= 20020

	periphPJLPESyntaxError11 TRAP-TYPE
		ENTERPRISE	netPrinter
		DESCRIPTION
			"PJL parser encountered an unsupported command
			 modifier."
	::= 20021

	periphPJLPESyntaxError12 TRAP-TYPE
		ENTERPRISE	netPrinter
		DESCRIPTION
			"PJL parser encountered a missing command
			 modifier."
	::= 20022

	periphPJLPESyntaxError13 TRAP-TYPE
		ENTERPRISE	netPrinter
		DESCRIPTION
			"PJL parser encountered a missing option."
	::= 20023

	periphPJLPESyntaxError14 TRAP-TYPE
		ENTERPRISE	netPrinter
		DESCRIPTION
			"PJL parser encountered extra data after 
			 an option name."
	::= 20024

	periphPJLPESyntaxError15 TRAP-TYPE
		ENTERPRISE	netPrinter
		DESCRIPTION
			"PJL parser encountered two decimal points
			 in a numeric value."
	::= 20025

	periphPJLPESyntaxError16 TRAP-TYPE
		ENTERPRISE	netPrinter
		DESCRIPTION
			"PJL parser encountered an invalid binary value."
	::= 20026


-- PJL Parser Warnings - a portion of the PJl command was ignored


	periphPJLPWGeneric TRAP-TYPE
		ENTERPRISE	netPrinter
		DESCRIPTION
			"PJL parser ignored part of a PJL command 
			 (generic warning)."
	::= 25001

	periphPJLPWPrefixMissing TRAP-TYPE
		ENTERPRISE	netPrinter
		DESCRIPTION
			"PJL parser ignored part of a PJL command 
			 because its prefix was missing."
	::= 25002

	periphPJLPWTooBig1 TRAP-TYPE
		ENTERPRISE	netPrinter
		DESCRIPTION
			"PJL parser ignored part of a PJL command 
			 because its alphanumeric value was too long."
	::= 25003

	periphPJLPWTooBig2 TRAP-TYPE
		ENTERPRISE	netPrinter
		DESCRIPTION
			"PJL parser ignored part of a PJL command 
			 because its string was too long."
	::= 25004

	periphPJLPWTooBig3 TRAP-TYPE
		ENTERPRISE	netPrinter
		DESCRIPTION
			"PJL parser ignored part of a PJL command 
			 because its numeric value was too long."
	::= 25005

	periphPJLPWOptionName1 TRAP-TYPE
		ENTERPRISE	netPrinter
		DESCRIPTION
			"PJL parser ignored part of a PJL command 
			 because its option name unsupported."
	::= 25006

	periphPJLPWOptionName2 TRAP-TYPE
		ENTERPRISE	netPrinter
		DESCRIPTION
			"PJL parser ignored part of a PJL command 
			 because its option name requires a value 
			 that was missing."
	::= 25007

	periphPJLPWOptionName3 TRAP-TYPE
		ENTERPRISE	netPrinter
		DESCRIPTION
			"PJL parser ignored part of a PJL command 
			 because its option name requires a value 
			 of a different type."
	::= 25008

	periphPJLPWOptionName4 TRAP-TYPE
		ENTERPRISE	netPrinter
		DESCRIPTION
			"PJL parser ignored part of a PJL command 
			 because its option name received a value 
			 but the option name doesn't support values."
	::= 25009

	periphPJLPWOptionName5 TRAP-TYPE
		ENTERPRISE	netPrinter
		DESCRIPTION
			"PJL parser ignored part of a PJL command 
			 because its option name was received more 
			 than once."
	::= 25010

	periphPJLPWOptionName6 TRAP-TYPE
		ENTERPRISE	netPrinter
		DESCRIPTION
			"PJL parser ignored part of a PJL command 
			 because its option value underflowed or
			 overflowed."
	::= 25011


	periphPJLPWOptionValue1 TRAP-TYPE
		ENTERPRISE	netPrinter
		DESCRIPTION
			"PJL Parser ignored the actual value of 
			 an option and used another value which
		 	 experienced data loss due to conversion."
	::= 25012

	periphPJLPWOptionValue2 TRAP-TYPE
		ENTERPRISE	netPrinter
		DESCRIPTION
			"PJL Parser ignored the actual value of 
			 an option because it was outside the 
			 valid range.  The PJL Parser used the
			 value at the closest supported limit."
	::= 25013

	periphPJLPWOptionValue3 TRAP-TYPE
		ENTERPRISE	netPrinter
		DESCRIPTION
			"PJL Parser ignored the actual value of 
			 an option because it was outside the 
			 valid range.  The value was ignored."
	::= 25014

	periphPJLPWOptionValue4 TRAP-TYPE
		ENTERPRISE	netPrinter
		DESCRIPTION
			"PJL Parser ignored the actual value of 
			 an option because it was an alphanumeric 
			 value, which is was not supported."
	::= 25016

	periphPJLPWOptionValue5 TRAP-TYPE
		ENTERPRISE	netPrinter
		DESCRIPTION
			"PJL Parser ignored the actual value of 
			 an option because it was an empty
			 string."
	::= 25017

	periphPJLPWUELNotFound TRAP-TYPE
		ENTERPRISE	netPrinter
		DESCRIPTION
			"PJL Parser did not receive a UEL command
			 when one was expected."
	::= 25018

-- PJL Semantic Errors - As much of the command was executed as possible

	periphPJLSEGeneric TRAP-TYPE
		ENTERPRISE	netPrinter
		DESCRIPTION
			"PJL Parser encountered a generic semantic
			 error."
	::= 27001

	periphPJLSEMismatchedEOJ TRAP-TYPE
		ENTERPRISE	netPrinter
		DESCRIPTION
			"PJL Parser encountered an EOJ command but
			 had not encountered a JOB command."
	::= 27002


	periphPJLSEPasswordProtected TRAP-TYPE
		ENTERPRISE	netPrinter
		DESCRIPTION
			"PJL Parser detected an attempt to change 
			 an NVRAM value without the proper password."
	::= 27003


	periphPJLSEReadOnly TRAP-TYPE
		ENTERPRISE	netPrinter
		DESCRIPTION
			"PJL Parser detected an attempt to change 
			 a read only value."
	::= 27004

	periphPJLSEDefaultOnly TRAP-TYPE
		ENTERPRISE	netPrinter
		DESCRIPTION
			"PJL Parser detected an attempt to change 
			 a value which can only use DEFAULT."
	::= 27005

	periphPJLSEStringCharError TRAP-TYPE
		ENTERPRISE	netPrinter
		DESCRIPTION
			"PJL Parser detected a null string when
  			 a string with at least one character
		 	 was required."
	::= 27006

	periphPJLSESetOnly TRAP-TYPE
		ENTERPRISE	netPrinter
		DESCRIPTION
			"PJL Parser detected an attempt to read 
			 a value which can only be settable."
	::= 27007


-- Auto-Continuable Conditions - conditions that are reported here 
-- the peripheral will recover from if the auto-continue flag is 
-- set to ON.  

	periphACCondition01 TRAP-TYPE
		ENTERPRISE	netPrinter
		DESCRIPTION
			"Status Buffer Overflow."
	::= 30010

	periphACCondition02 TRAP-TYPE
		ENTERPRISE	netPrinter
		DESCRIPTION
			"Memory Overflow."
	::= 30016

	periphACCondition03 TRAP-TYPE
		ENTERPRISE	netPrinter
		DESCRIPTION
			"Print Overrun."
	::= 30017

	periphACCondition04 TRAP-TYPE
		ENTERPRISE	netPrinter
		DESCRIPTION
			"40 Error."
	::= 30018

	periphACCondition05 TRAP-TYPE
		ENTERPRISE	netPrinter
		DESCRIPTION
			"22 I/O Config Error."
	::= 30027

	periphACCondition06 TRAP-TYPE
		ENTERPRISE	netPrinter
		DESCRIPTION
			"41.x Error."
	::= 30034	
	
	periphACCondition07 TRAP-TYPE
		ENTERPRISE	netPrinter
		DESCRIPTION
			"68 Error Check Configuration."
	::= 30035

	periphACCondition08 TRAP-TYPE
		ENTERPRISE	netPrinter
		DESCRIPTION
			"68 Service."
	::= 30036

	periphACCondition09 TRAP-TYPE
		ENTERPRISE	netPrinter
		DESCRIPTION
			"49 Remove Page."
	::= 30072

	periphACCondition10 TRAP-TYPE
		ENTERPRISE	netPrinter
		DESCRIPTION
			"Personality Memory Overflow."
	::= 30076

	periphACCondition11 TRAP-TYPE
		ENTERPRISE	netPrinter
		DESCRIPTION
			"41.1 General Misprint Error."
	::= 30094

	periphACCondition12 TRAP-TYPE
		ENTERPRISE	netPrinter
		DESCRIPTION
			"41.2 Beam Detect Malfunction."
	::= 30095

	periphACCondition13 TRAP-TYPE
		ENTERPRISE	netPrinter
		DESCRIPTION
			"41.3 Improper Paper Size."
	::= 30096

	periphACCondition14 TRAP-TYPE
		ENTERPRISE	netPrinter
		DESCRIPTION
			"41.4 No Video Sync."
	::= 30097	
	
	periphACCondition15 TRAP-TYPE
		ENTERPRISE	netPrinter
		DESCRIPTION
			"41.5 Noisy Video Sync Req Signal."
	::= 30098

	periphACCondition16 TRAP-TYPE
		ENTERPRISE	netPrinter
		DESCRIPTION
			"Invalid Input Source."
	::= 30099

	periphACCondition17 TRAP-TYPE
		ENTERPRISE	netPrinter
		DESCRIPTION
			"Invalid Output Destination."
	::= 30100

	periphACCondition18 TRAP-TYPE
		ENTERPRISE	netPrinter
		DESCRIPTION
			"Binding Agent Out of Supplies."
	::= 30101

	periphACCondition19 TRAP-TYPE
		ENTERPRISE	netPrinter
		DESCRIPTION
			"Binding Agent Media Misalignment."
	::= 30102

	periphACCondition20 TRAP-TYPE
		ENTERPRISE	netPrinter
		DESCRIPTION
			"Binding Agent Media Misalignment."
	::= 30103

	periphACCondition21 TRAP-TYPE
		ENTERPRISE	netPrinter
		DESCRIPTION
			"External Input Device."
	::= 30104

	periphACCondition22 TRAP-TYPE
		ENTERPRISE	netPrinter
		DESCRIPTION
			"External Output Device Paper Path 
			 Error."
	::= 30105

	periphACCondition23 TRAP-TYPE
		ENTERPRISE	netPrinter
		DESCRIPTION
			"External Input Device Operational 
			 Error."
	::= 30106

	periphACCondition24 TRAP-TYPE
		ENTERPRISE	netPrinter
		DESCRIPTION
			"External Output Device Operational 
			 Error."
	::= 30107

	periphACCondition25 TRAP-TYPE
		ENTERPRISE	netPrinter
		DESCRIPTION
			"40 HP MIO Error - Press Go Key."
	::= 30108

	periphACCondition26 TRAP-TYPE
		ENTERPRISE	netPrinter
		DESCRIPTION
			"40 Bad Serial Data Format - Press Go Key."
	::= 30109

	periphACCondition27 TRAP-TYPE
		ENTERPRISE	netPrinter
		DESCRIPTION
			"22 HP MIO Error - Press Go Key."
	::= 30110

	periphACCondition28 TRAP-TYPE
		ENTERPRISE	netPrinter
		DESCRIPTION
			"22 Parallel I/O Error - Press Go Key."
	::= 30111

	periphACCondition29 TRAP-TYPE
		ENTERPRISE	netPrinter
		DESCRIPTION
			"22 Serial I/O Error - Press Go Key."
	::= 30112

	periphACCondition30 TRAP-TYPE
		ENTERPRISE	netPrinter
		DESCRIPTION
			"Stopping - Check Last Page."
	::= 30113

	periphACCondition31 TRAP-TYPE
		ENTERPRISE	netPrinter
		DESCRIPTION
			"Press Select to Cancel Job."
	::= 30114

	periphACCondition32 TRAP-TYPE
		ENTERPRISE	netPrinter
		DESCRIPTION
			"Volume 1 Disk Not Initialized."
	::= 30115

	periphACCondition33 TRAP-TYPE
		ENTERPRISE	netPrinter
		DESCRIPTION
			"Volume 1 Disk Failure."
	::= 30116

	periphACCondition34 TRAP-TYPE
		ENTERPRISE	netPrinter
		DESCRIPTION
			"Volume 2 Disk Not Initialized."
	::= 30117

	periphACCondition35 TRAP-TYPE
		ENTERPRISE	netPrinter
		DESCRIPTION
			"Volume 2 Disk Failure."
	::= 30118

	periphACCondition36 TRAP-TYPE
		ENTERPRISE	netPrinter
		DESCRIPTION
			"Media Feed Error."
	::= 30119

-- PJL File System Errors

	periphPJLFSError01 TRAP-TYPE
		ENTERPRISE	netPrinter
		DESCRIPTION
			"General Error."
	::= 32000

	periphPJLFSError02 TRAP-TYPE
		ENTERPRISE	netPrinter
		DESCRIPTION
			"Volume Not Available."
	::= 32001

	periphPJLFSError03 TRAP-TYPE
		ENTERPRISE	netPrinter
		DESCRIPTION
			"Disk Full."
	::= 32002

	periphPJLFSError04 TRAP-TYPE
		ENTERPRISE	netPrinter
		DESCRIPTION
			"File Not Found."
	::= 32003

	periphPJLFSError05 TRAP-TYPE
		ENTERPRISE	netPrinter
		DESCRIPTION
			"No Free File Descriptors."
	::= 32004

	periphPJLFSError06 TRAP-TYPE
		ENTERPRISE	netPrinter
		DESCRIPTION
			"Invalid Number of Bytes."
	::= 32005

	periphPJLFSError07 TRAP-TYPE
		ENTERPRISE	netPrinter
		DESCRIPTION
			"File Already Exists."
	::= 32006

	periphPJLFSError08 TRAP-TYPE
		ENTERPRISE	netPrinter
		DESCRIPTION
			"Illegal Name."
	::= 32007

	periphPJLFSError09 TRAP-TYPE
		ENTERPRISE	netPrinter
		DESCRIPTION
			"Can't Delete Root."
	::= 32008

	periphPJLFSError10 TRAP-TYPE
		ENTERPRISE	netPrinter
		DESCRIPTION
			"File Operation Attempted On
			 a Directory."
	::= 32009

	periphPJLFSError11 TRAP-TYPE
		ENTERPRISE	netPrinter
		DESCRIPTION
			"Directory operation attempted
			 on a file."
	::= 32010

	periphPJLFSError12 TRAP-TYPE
		ENTERPRISE	netPrinter
		DESCRIPTION
			"Not same volume."
	::= 32011

	periphPJLFSError13 TRAP-TYPE
		ENTERPRISE	netPrinter
		DESCRIPTION
			"Read Only."
	::= 32012

	periphPJLFSError14 TRAP-TYPE
		ENTERPRISE	netPrinter
		DESCRIPTION
			"Directory Full."
	::= 32013

	periphPJLFSError15 TRAP-TYPE
		ENTERPRISE	netPrinter
		DESCRIPTION
			"Directory not empty."
	::= 32014

	periphPJLFSError16 TRAP-TYPE
		ENTERPRISE	netPrinter
		DESCRIPTION
			"Bad Disk."
	::= 32015

	periphPJLFSError17 TRAP-TYPE
		ENTERPRISE	netPrinter
		DESCRIPTION
			"No Label."
	::= 32016

	periphPJLFSError18 TRAP-TYPE
		ENTERPRISE	netPrinter
		DESCRIPTION
			"Invalid Parameter."
	::= 32017

	periphPJLFSError19 TRAP-TYPE
		ENTERPRISE	netPrinter
		DESCRIPTION
			"No contiguous space."
	::= 32018

	periphPJLFSError20 TRAP-TYPE
		ENTERPRISE	netPrinter
		DESCRIPTION
			"Can't change root."
	::= 32019

	periphPJLFSError21 TRAP-TYPE
		ENTERPRISE	netPrinter
		DESCRIPTION
			"File Descriptor obsolete."
	::= 32020

	periphPJLFSError22 TRAP-TYPE
		ENTERPRISE	netPrinter
		DESCRIPTION
			"Deleted."
	::= 32021

	periphPJLFSError23 TRAP-TYPE
		ENTERPRISE	netPrinter
		DESCRIPTION
			"No Block Device."
	::= 32022

	periphPJLFSError24 TRAP-TYPE
		ENTERPRISE	netPrinter
		DESCRIPTION
			"Bad Seek."
	::= 32023

	periphPJLFSError25 TRAP-TYPE
		ENTERPRISE	netPrinter
		DESCRIPTION
			"Internal Error."
	::= 32024

	periphPJLFSError26 TRAP-TYPE
		ENTERPRISE	netPrinter
		DESCRIPTION
			"Write Only."
	::= 32025

	periphPJLFSError27 TRAP-TYPE
		ENTERPRISE	netPrinter
		DESCRIPTION
			"Write Protected."
	::= 32026

	periphPJLFSError28 TRAP-TYPE
		ENTERPRISE	netPrinter
		DESCRIPTION
			"No Filename."
	::= 32027

	periphPJLFSError29 TRAP-TYPE
		ENTERPRISE	netPrinter
		DESCRIPTION
			"Error Base 2."
	::= 32050

	periphPJLFSError30 TRAP-TYPE
		ENTERPRISE	netPrinter
		DESCRIPTION
			"End of directory."
	::= 32051

	periphPJLFSError31 TRAP-TYPE
		ENTERPRISE	netPrinter
		DESCRIPTION
			"No File System."
	::= 32052

	periphPJLFSError32 TRAP-TYPE
		ENTERPRISE	netPrinter
		DESCRIPTION
			"No memory."
	::= 32053

	periphPJLFSError33 TRAP-TYPE
		ENTERPRISE	netPrinter
		DESCRIPTION
			"Volume Name out of range."
	::= 32054

	periphPJLFSError34 TRAP-TYPE
		ENTERPRISE	netPrinter
		DESCRIPTION
			"Bad FS."
	::= 32055

	periphPJLFSError35 TRAP-TYPE
		ENTERPRISE	netPrinter
		DESCRIPTION
			"Hardware Failure."
	::= 32056

	periphPJLFSError36 TRAP-TYPE
		ENTERPRISE	netPrinter
		DESCRIPTION
			"Not a descriptor."
	::= 32057

	periphPJLFSError37 TRAP-TYPE
		ENTERPRISE	netPrinter
		DESCRIPTION
			"File Locked."
	::= 32058

	periphPJLFSError38 TRAP-TYPE
		ENTERPRISE	netPrinter
		DESCRIPTION
			"Maximum Directories."
	::= 32059

	periphPJLFSError39 TRAP-TYPE
		ENTERPRISE	netPrinter
		DESCRIPTION
			"Already Open."
	::= 32060

	periphPJLFSError40 TRAP-TYPE
		ENTERPRISE	netPrinter
		DESCRIPTION
			"Bad IOCTL."
	::= 32061

	periphPJLFSError41 TRAP-TYPE
		ENTERPRISE	netPrinter
		DESCRIPTION
			"No Volume Label."
	::= 32062

	periphPJLFSError42 TRAP-TYPE
		ENTERPRISE	netPrinter
		DESCRIPTION
			"File Not New."
	::= 32063

	periphPJLFSError43 TRAP-TYPE
		ENTERPRISE	netPrinter
		DESCRIPTION
			"Access Denied."
	::= 32064

	periphPJLFSError44 TRAP-TYPE
		ENTERPRISE	netPrinter
		DESCRIPTION
			"Locked."
	::= 32065

	periphPJLFSError45 TRAP-TYPE
		ENTERPRISE	netPrinter
		DESCRIPTION
			"Not Locked."
	::= 32066

	periphPJLFSError46 TRAP-TYPE
		ENTERPRISE	netPrinter
		DESCRIPTION
			"Re-Queue."
	::= 32067

	periphPJLFSError47 TRAP-TYPE
		ENTERPRISE	netPrinter
		DESCRIPTION
			"Would Block."
	::= 32068

-- Potential Operator Intervention Conditions

	periphPOICondition01 TRAP-TYPE
		ENTERPRISE	netPrinter
		DESCRIPTION
			"Bad MIO/EIO."
	::= 35028

	periphPOICondition02 TRAP-TYPE
		ENTERPRISE	netPrinter
		DESCRIPTION
			"W1 Image Adapt/Assist"
	::= 35029

	periphPOICondition03 TRAP-TYPE
		ENTERPRISE	netPrinter
		DESCRIPTION
			"Envelope Changed"
	::= 35030

	periphPOICondition04 TRAP-TYPE
		ENTERPRISE	netPrinter
		DESCRIPTION
			"W2 Invalid Personality"
	::= 35031

	periphPOICondition05 TRAP-TYPE
		ENTERPRISE	netPrinter
		DESCRIPTION
			"WL Warning Lost"
	::= 35032

	periphPOICondition06 TRAP-TYPE
		ENTERPRISE	netPrinter
		DESCRIPTION
			"W3 Job Aborting"
	::= 35037

	periphPOICondition07 TRAP-TYPE
		ENTERPRISE	netPrinter
		DESCRIPTION
			"W9 Job 600/LTR"
	::= 35039

	periphPOICondition08 TRAP-TYPE
		ENTERPRISE	netPrinter
		DESCRIPTION
			"W0 Job 600/A4"
	::= 35040

	periphPOICondition09 TRAP-TYPE
		ENTERPRISE	netPrinter
		DESCRIPTION
			"W8 Job 600/OFF"
	::= 35041

	periphPOICondition10 TRAP-TYPE
		ENTERPRISE	netPrinter
		DESCRIPTION
			"W7 Job 300/LGL"
	::= 35042

	periphPOICondition11 TRAP-TYPE
		ENTERPRISE	netPrinter
		DESCRIPTION
			"W5 Job 300/LTR"
	::= 35043

	periphPOICondition12 TRAP-TYPE
		ENTERPRISE	netPrinter
		DESCRIPTION
			"W6 Job 300/A4"
	::= 35044

	periphPOICondition13 TRAP-TYPE
		ENTERPRISE	netPrinter
		DESCRIPTION
			"W4 Job 300/OFF"
	::= 35045

	periphPOICondition14 TRAP-TYPE
		ENTERPRISE	netPrinter
		DESCRIPTION
			"WM Check Memory Configuration"
	::= 35073

	periphPOICondition15 TRAP-TYPE
		ENTERPRISE	netPrinter
		DESCRIPTION
			"WM Memory Configuration N/A"
	::= 35074

	periphPOICondition16 TRAP-TYPE
		ENTERPRISE	netPrinter
		DESCRIPTION
			"User Maintence Requested"
	::= 35075

	periphPOICondition17 TRAP-TYPE
		ENTERPRISE	netPrinter
		DESCRIPTION
			"WM <personality> Memory Full"
	::= 35076

	periphPOICondition18 TRAP-TYPE
		ENTERPRISE	netPrinter
		DESCRIPTION
			"Entered Powersave Mode"
	::= 35078

	periphPOICondition19 TRAP-TYPE
		ENTERPRISE	netPrinter
		DESCRIPTION
			"WM Job 300"
	::= 35081

	periphPOICondition20 TRAP-TYPE
		ENTERPRISE	netPrinter
		DESCRIPTION
			"WD Disk Not Initialized"
	::= 35082

	periphPOICondition21 TRAP-TYPE
		ENTERPRISE	netPrinter
		DESCRIPTION
			"WM Job 600/LGL"
	::= 35084

	periphPOICondition22 TRAP-TYPE
		ENTERPRISE	netPrinter
		DESCRIPTION
			"WM Job 600/A3"
	::= 35085

	periphPOICondition23 TRAP-TYPE
		ENTERPRISE	netPrinter
		DESCRIPTION
			"WM Job 600/11x17"
	::= 35086

	periphPOICondition24 TRAP-TYPE
		ENTERPRISE	netPrinter
		DESCRIPTION
			"WM Job 300/A3"
	::= 35087

	periphPOICondition25 TRAP-TYPE
		ENTERPRISE	netPrinter
		DESCRIPTION
			"WM Job 300/11x17"
	::= 35088

	periphPOICondition26 TRAP-TYPE
		ENTERPRISE	netPrinter
		DESCRIPTION
			"WD Disk Not Initialized Vol 1"
	::= 35115

	periphPOICondition27 TRAP-TYPE
		ENTERPRISE	netPrinter
		DESCRIPTION
			"WD Disk Not Initialized Vol 2"
	::= 35117

	periphPOICondition28 TRAP-TYPE
		ENTERPRISE	netPrinter
		DESCRIPTION
			"MOPY failure due to disk error"
	::= 35138

	periphPOICondition29 TRAP-TYPE
		ENTERPRISE	netPrinter
		DESCRIPTION
			"MOPY failure due to insufficient 
			 disk space."
	::= 35139

	periphPOICondition30 TRAP-TYPE
		ENTERPRISE	netPrinter
		DESCRIPTION
			"MOPY failure due to incorrect 
			 firmware configuration."
	::= 35140

-- Operator Intervention Conditions

	periphOICondition01 TRAP-TYPE
		ENTERPRISE	netPrinter
		DESCRIPTION
			"Sleep Mode (Standby)."
	::= 40000

	periphOICondition02 TRAP-TYPE
		ENTERPRISE	netPrinter
		DESCRIPTION
			"Cartridge error during alignment."
	::= 40005

	periphOICondition03 TRAP-TYPE
		ENTERPRISE	netPrinter
		DESCRIPTION
			"No Toner Cartridge."
	::= 40010

	periphOICondition04 TRAP-TYPE
		ENTERPRISE	netPrinter
		DESCRIPTION
			"Accessing Ink Cartridges."
	::= 40011

	periphOICondition05 TRAP-TYPE
		ENTERPRISE	netPrinter
		DESCRIPTION
			"Remove Paper From <bin name>."
	::= 40019

	periphOICondition06 TRAP-TYPE
		ENTERPRISE	netPrinter
		DESCRIPTION
			"No Micr. Toner."
	::= 40020

	periphOICondition07 TRAP-TYPE
		ENTERPRISE	netPrinter
		DESCRIPTION
			"Close Printer Cover or lower lever/window."
	::= 40021

	periphOICondition08 TRAP-TYPE
		ENTERPRISE	netPrinter
		DESCRIPTION
			"Paper Jam."
	::= 40022

	periphOICondition09 TRAP-TYPE
		ENTERPRISE	netPrinter
		DESCRIPTION
			"FE Cartridge."
	::= 40024

	periphOICondition10 TRAP-TYPE
		ENTERPRISE	netPrinter
		DESCRIPTION
			"PC Install."
	::= 40026

	periphOICondition11 TRAP-TYPE
		ENTERPRISE	netPrinter
		DESCRIPTION
			"Toner Low."
	::= 40038

	periphOICondition12 TRAP-TYPE
		ENTERPRISE	netPrinter
		DESCRIPTION
			"FI Insert Cart."
	::= 40046

	periphOICondition13 TRAP-TYPE
		ENTERPRISE	netPrinter
		DESCRIPTION
			"FR Remove Cart."
	::= 40047

	periphOICondition14 TRAP-TYPE
		ENTERPRISE	netPrinter
		DESCRIPTION
			"[PJL OPMSG]."
	::= 40048

	periphOICondition15 TRAP-TYPE
		ENTERPRISE	netPrinter
		DESCRIPTION
			"[PJL STMSG]."
	::= 40049

	periphOICondition16 TRAP-TYPE
		ENTERPRISE	netPrinter
		DESCRIPTION
			"50 Service."
	::= 40050

	periphOICondition17 TRAP-TYPE
		ENTERPRISE	netPrinter
		DESCRIPTION
			"51 Error."
	::= 40051

	periphOICondition18 TRAP-TYPE
		ENTERPRISE	netPrinter
		DESCRIPTION
			"52 Error."
	::= 40052

	periphOICondition19 TRAP-TYPE
		ENTERPRISE	netPrinter
		DESCRIPTION
			"53-xy-zz Error."
	::= 40053

	periphOICondition20 TRAP-TYPE
		ENTERPRISE	netPrinter
		DESCRIPTION
			"54 Error."
	::= 40054

	periphOICondition21 TRAP-TYPE
		ENTERPRISE	netPrinter
		DESCRIPTION
			"55 Error."
	::= 40055

	periphOICondition22 TRAP-TYPE
		ENTERPRISE	netPrinter
		DESCRIPTION
			"56 Error."
	::= 40056

	periphOICondition23 TRAP-TYPE
		ENTERPRISE	netPrinter
		DESCRIPTION
			"57 Service."
	::= 40057

	periphOICondition24 TRAP-TYPE
		ENTERPRISE	netPrinter
		DESCRIPTION
			"58 Service."
	::= 40058

	periphOICondition25 TRAP-TYPE
		ENTERPRISE	netPrinter
		DESCRIPTION
			"59 Error."
	::= 40059

	periphOICondition26 TRAP-TYPE
		ENTERPRISE	netPrinter
		DESCRIPTION
			"60.x Service."
	::= 40060

	periphOICondition27 TRAP-TYPE
		ENTERPRISE	netPrinter
		DESCRIPTION
			"61.x Service."
	::= 40061

	periphOICondition28 TRAP-TYPE
		ENTERPRISE	netPrinter
		DESCRIPTION
			"62.x Service."
	::= 40062

	periphOICondition29 TRAP-TYPE
		ENTERPRISE	netPrinter
		DESCRIPTION
			"63 Service."
	::= 40063

	periphOICondition30 TRAP-TYPE
		ENTERPRISE	netPrinter
		DESCRIPTION
			"64 Service."
	::= 40064

	periphOICondition31 TRAP-TYPE
		ENTERPRISE	netPrinter
		DESCRIPTION
			"65 Service."
	::= 40065

	periphOICondition32 TRAP-TYPE
		ENTERPRISE	netPrinter
		DESCRIPTION
			"67 Service."
	::= 40067

	periphOICondition33 TRAP-TYPE
		ENTERPRISE	netPrinter
		DESCRIPTION
			"69 Service."
	::= 40068

	periphOICondition34 TRAP-TYPE
		ENTERPRISE	netPrinter
		DESCRIPTION
			"70 Error."
	::= 40069

	periphOICondition35 TRAP-TYPE
		ENTERPRISE	netPrinter
		DESCRIPTION
			"71 Error."
	::= 40070

	periphOICondition36 TRAP-TYPE
		ENTERPRISE	netPrinter
		DESCRIPTION
			"72 Service."
	::= 40071

	periphOICondition37 TRAP-TYPE
		ENTERPRISE	netPrinter
		DESCRIPTION
			"Offline/Formfeeding/Service Mode."
	::= 40079

	periphOICondition38 TRAP-TYPE
		ENTERPRISE	netPrinter
		DESCRIPTION
			"EE/LC Incompatible."
	::= 40080

	periphOICondition39 TRAP-TYPE
		ENTERPRISE	netPrinter
		DESCRIPTION
			"FS Disk Failure."
	::= 40083

	periphOICondition40 TRAP-TYPE
		ENTERPRISE	netPrinter
		DESCRIPTION
			"Incomplete Tray 4 Installed."
	::= 40089

	periphOICondition41 TRAP-TYPE
		ENTERPRISE	netPrinter
		DESCRIPTION
			"Incomplete Envelope Feeder Installed."
	::= 40090

	periphOICondition42 TRAP-TYPE
		ENTERPRISE	netPrinter
		DESCRIPTION
			"81 Service Error."
	::= 40092

	periphOICondition43 TRAP-TYPE
		ENTERPRISE	netPrinter
		DESCRIPTION
			"Remove Duplex Jam."
	::= 40093

	periphOICondition44 TRAP-TYPE
		ENTERPRISE	netPrinter
		DESCRIPTION
			"56.1 Error."
	::= 40099

	periphOICondition45 TRAP-TYPE
		ENTERPRISE	netPrinter
		DESCRIPTION
			"56.2 Error."
	::= 40100

	periphOICondition46 TRAP-TYPE
		ENTERPRISE	netPrinter
		DESCRIPTION
			"Finisher Align Error."
	::= 40102

	periphOICondition47 TRAP-TYPE
		ENTERPRISE	netPrinter
		DESCRIPTION
			"Finish Limit Reached."
	::= 40103

	periphOICondition48 TRAP-TYPE
		ENTERPRISE	netPrinter
		DESCRIPTION
			"Input Device Feed Path Open."
	::= 40104

	periphOICondition49 TRAP-TYPE
		ENTERPRISE	netPrinter
		DESCRIPTION
			"Output Device Delivery Path Open."
	::= 40105

	periphOICondition50 TRAP-TYPE
		ENTERPRISE	netPrinter
		DESCRIPTION
			"Input Operation Error."
	::= 40106

	periphOICondition51 TRAP-TYPE
		ENTERPRISE	netPrinter
		DESCRIPTION
			"Output Operation Error."
	::= 40107

	periphOICondition52 TRAP-TYPE
		ENTERPRISE	netPrinter
		DESCRIPTION
			"Volume 1 Failure."
	::= 40116

	periphOICondition53 TRAP-TYPE
		ENTERPRISE	netPrinter
		DESCRIPTION
			"Volume 2 Failure."
	::= 40118

	periphOICondition54 TRAP-TYPE
		ENTERPRISE	netPrinter
		DESCRIPTION
			"Media Feed Error."
	::= 40119

	periphOICondition55 TRAP-TYPE
		ENTERPRISE	netPrinter
		DESCRIPTION
			"Open Face Up Output Bin."
	::= 40120

	periphOICondition56 TRAP-TYPE
		ENTERPRISE	netPrinter
		DESCRIPTION
			"Close Face Up Output Bin."
	::= 40121

	periphOICondition57 TRAP-TYPE
		ENTERPRISE	netPrinter
		DESCRIPTION
			"Duplexer Must Be Installed."
	::= 40122

	periphOICondition58 TRAP-TYPE
		ENTERPRISE	netPrinter
		DESCRIPTION
			"Duplexer error - remove duplexer."
	::= 40123

	periphOICondition59 TRAP-TYPE
		ENTERPRISE	netPrinter
		DESCRIPTION
			"bad duplexer connection."
	::= 40124

	periphOICondition60 TRAP-TYPE
		ENTERPRISE	netPrinter
		DESCRIPTION
			"bad size reported by tray 2."
	::= 40125

	periphOICondition61 TRAP-TYPE
		ENTERPRISE	netPrinter
		DESCRIPTION
			"bad size reported by tray 3."
	::= 40126

	periphOICondition62 TRAP-TYPE
		ENTERPRISE	netPrinter
		DESCRIPTION
			"too many mass storage devices."
	::= 40127

	periphOICondition63 TRAP-TYPE
		ENTERPRISE	netPrinter
		DESCRIPTION
			"drum error."
	::= 40128

	periphOICondition64 TRAP-TYPE
		ENTERPRISE	netPrinter
		DESCRIPTION
			"drum life out."
	::= 40129

	periphOICondition65 TRAP-TYPE
		ENTERPRISE	netPrinter
		DESCRIPTION
			"drum life low."
	::= 40130

	periphOICondition66 TRAP-TYPE
		ENTERPRISE	netPrinter
		DESCRIPTION
			"transfer kit out."
	::= 40131

	periphOICondition67 TRAP-TYPE
		ENTERPRISE	netPrinter
		DESCRIPTION
			"transfer kit low."
	::= 40132

	periphOICondition68 TRAP-TYPE
		ENTERPRISE	netPrinter
		DESCRIPTION
			"clean density sensor - cycle power."
	::= 40133

	periphOICondition69 TRAP-TYPE
		ENTERPRISE	netPrinter
		DESCRIPTION
			"lock toner level."
	::= 40134

	periphOICondition70 TRAP-TYPE
		ENTERPRISE	netPrinter
		DESCRIPTION
			"press select if transfer is new."
	::= 40135

	periphOICondition71 TRAP-TYPE
		ENTERPRISE	netPrinter
		DESCRIPTION
			"press select if fuser is new."
	::= 40136

	periphOICondition72 TRAP-TYPE
		ENTERPRISE	netPrinter
		DESCRIPTION
			"bad envelope feeder connection."
	::= 40137

-- Foreground Paper Loading - operator intervention needed
-- to provide the correct media and size to start/complete
-- the print job

-- unknown paper  

	periphFPLMPTrayUnknownPaper TRAP-TYPE
		ENTERPRISE	netPrinter
		DESCRIPTION
			"The peripheral is waiting for the operator 
			 to load paper of an unknown size in the
			 MP tray or envelope tray."
	::= 41000

	periphFPLManualFeedUnknownPaper TRAP-TYPE
		ENTERPRISE	netPrinter
		DESCRIPTION
			"The peripheral is waiting for the operator 
			 to load paper of an unknown size in the
			 manual feed tray."
	::= 41100

	periphFPLPCTrayUnknownPaper TRAP-TYPE
		ENTERPRISE	netPrinter
		DESCRIPTION
			"The peripheral is waiting for the operator 
			 to load paper of an unknown size in the
			 PC tray or universal tray 2."
	::= 41200

	periphFPLLCTrayUnknownPaper TRAP-TYPE
		ENTERPRISE	netPrinter
		DESCRIPTION
			"The peripheral is waiting for the operator 
			 to load paper of an unknown size in the
			 LC tray or universal tray 3."
	::= 41300

	periphFPLEETrayUnknownPaper TRAP-TYPE
		ENTERPRISE	netPrinter
		DESCRIPTION
			"The peripheral is waiting for the operator 
			 to load paper of an unknown size in the
			 EE tray or envelope feeder."
	::= 41400

	periphFPLHCITray4UnknownPaper TRAP-TYPE
		ENTERPRISE	netPrinter
		DESCRIPTION
			"The peripheral is waiting for the operator 
			 to load paper of an unknown size in hci tray 4."
	::= 41500

	periphFPLHCITray5UnknownPaper TRAP-TYPE
		ENTERPRISE	netPrinter
		DESCRIPTION
			"The peripheral is waiting for the operator 
			 to load paper of an unknown size in hci tray 5."
	::= 41600

	periphFPLHCITray6UnknownPaper TRAP-TYPE
		ENTERPRISE	netPrinter
		DESCRIPTION
			"The peripheral is waiting for the operator 
			 to load paper of an unknown size in hci tray 6."
	::= 41700

	periphFPLHCITray7UnknownPaper TRAP-TYPE
		ENTERPRISE	netPrinter
		DESCRIPTION
			"The peripheral is waiting for the operator 
			 to load paper of an unknown size in hci tray 7."
	::= 41800

	periphFPLHCITray8OrAllUnknownPaper TRAP-TYPE
		ENTERPRISE	netPrinter
		DESCRIPTION
			"The peripheral is waiting for the operator 
			 to load paper of an unknown size in hci tray 8
			 or all input trays are out of paper."
	::= 41900


-- unknown envelope  

	periphFPLMPTrayUnknownEnvelope TRAP-TYPE
		ENTERPRISE	netPrinter
		DESCRIPTION
			"The peripheral is waiting for the operator 
			 to load an envelope of an unknown size in the
			 MP tray or envelope tray."
	::= 41001

	periphFPLManualFeedUnknownEnvelope TRAP-TYPE
		ENTERPRISE	netPrinter
		DESCRIPTION
			"The peripheral is waiting for the operator 
			 to load an envelope of an unknown size in the
			 manual feed tray."
	::= 41101

	periphFPLPCTrayUnknownEnvelope TRAP-TYPE
		ENTERPRISE	netPrinter
		DESCRIPTION
			"The peripheral is waiting for the operator 
			 to load an envelope of an unknown size in the
			 PC tray or universal tray 2."
	::= 41201

	periphFPLLCTrayUnknownEnvelope TRAP-TYPE
		ENTERPRISE	netPrinter
		DESCRIPTION
			"The peripheral is waiting for the operator 
			 to load an envelope of an unknown size in the
			 LC tray or universal tray 3."
	::= 41301

	periphFPLEETrayUnknownEnvelope TRAP-TYPE
		ENTERPRISE	netPrinter
		DESCRIPTION
			"The peripheral is waiting for the operator 
			 to load an envelope of an unknown size in the
			 EE tray or envelope feeder."
	::= 41401

	periphFPLHCITray4UnknownEnvelope TRAP-TYPE
		ENTERPRISE	netPrinter
		DESCRIPTION
			"The peripheral is waiting for the operator 
			 to load an envelope of an unknown size in hci tray 4."
	::= 41501

	periphFPLHCITray5UnknownEnvelope TRAP-TYPE
		ENTERPRISE	netPrinter
		DESCRIPTION
			"The peripheral is waiting for the operator 
			 to load an envelope of an unknown size in hci tray 5."
	::= 41601

	periphFPLHCITrayUnknownEnvelope TRAP-TYPE
		ENTERPRISE	netPrinter
		DESCRIPTION
			"The peripheral is waiting for the operator 
			 to load an envelope of an unknown size in hci tray 6."
	::= 41701

	periphFPLHCITray7UnknownEnvelope TRAP-TYPE
		ENTERPRISE	netPrinter
		DESCRIPTION
			"The peripheral is waiting for the operator 
			 to load an envelope of an unknown size in hci tray 7."
	::= 41801

	periphFPLHCITray8OrAllUnknownEnvelope TRAP-TYPE
		ENTERPRISE	netPrinter
		DESCRIPTION
			"The peripheral is waiting for the operator 
			 to load an envelope of an unknown size in hci tray 8
			 or all input trays are out of media."
	::= 41901


-- letter paper  

	periphFPLMPTrayLetterPaper TRAP-TYPE
		ENTERPRISE	netPrinter
		DESCRIPTION
			"The peripheral is waiting for the operator 
			 to load paper of letter size in the
			 MP tray or envelope tray."
	::= 41002

	periphFPLManualFeedLetterPaper TRAP-TYPE
		ENTERPRISE	netPrinter
		DESCRIPTION
			"The peripheral is waiting for the operator 
			 to load paper of letter size in the
			 manual feed tray."
	::= 41102

	periphFPLPCTrayLetterPaper TRAP-TYPE
		ENTERPRISE	netPrinter
		DESCRIPTION
			"The peripheral is waiting for the operator 
			 to load paper of letter size in the
			 PC tray or universal tray 2."
	::= 41202

	periphFPLLCTrayLetterPaper TRAP-TYPE
		ENTERPRISE	netPrinter
		DESCRIPTION
			"The peripheral is waiting for the operator 
			 to load paper of letter size in the
			 LC tray or universal tray 3."
	::= 41302

	periphFPLEETrayLetterPaper TRAP-TYPE
		ENTERPRISE	netPrinter
		DESCRIPTION
			"The peripheral is waiting for the operator 
			 to load paper of letter size in the
			 EE tray or envelope feeder."
	::= 41402

	periphFPLHCITray4LetterPaper TRAP-TYPE
		ENTERPRISE	netPrinter
		DESCRIPTION
			"The peripheral is waiting for the operator 
			 to load paper of letter size in hci tray 4."
	::= 41502

	periphFPLHCITray5LetterPaper TRAP-TYPE
		ENTERPRISE	netPrinter
		DESCRIPTION
			"The peripheral is waiting for the operator 
			 to load paper of letter size in hci tray 5."
	::= 41602

	periphFPLHCITray6LetterPaper TRAP-TYPE
		ENTERPRISE	netPrinter
		DESCRIPTION
			"The peripheral is waiting for the operator 
			 to load paper of letter size in hci tray 6."
	::= 41702

	periphFPLHCITray7LetterPaper TRAP-TYPE
		ENTERPRISE	netPrinter
		DESCRIPTION
			"The peripheral is waiting for the operator 
			 to load paper of letter size in hci tray 7."
	::= 41802

	periphFPLHCITray8OrAllLetterPaper TRAP-TYPE
		ENTERPRISE	netPrinter
		DESCRIPTION
			"The peripheral is waiting for the operator 
			 to load paper of letter size in hci tray 8 
			 or all input trays our out of media."
	::= 41902


-- legal paper  

	periphFPLMPTrayLegalPaper TRAP-TYPE
		ENTERPRISE	netPrinter
		DESCRIPTION
			"The peripheral is waiting for the operator 
			 to load paper of legal size in the
			 MP tray or envelope tray."
	::= 41003

	periphFPLManualFeedLegalPaper TRAP-TYPE
		ENTERPRISE	netPrinter
		DESCRIPTION
			"The peripheral is waiting for the operator 
			 to load paper of legal size in the
			 manual feed tray."
	::= 41103

	periphFPLPCTrayLegalPaper TRAP-TYPE
		ENTERPRISE	netPrinter
		DESCRIPTION
			"The peripheral is waiting for the operator 
			 to load paper of legal size in the
			 PC tray or universal tray 2."
	::= 41203

	periphFPLLCTrayLegalPaper TRAP-TYPE
		ENTERPRISE	netPrinter
		DESCRIPTION
			"The peripheral is waiting for the operator 
			 to load paper of legal size in the
			 LC tray or universal tray 3."
	::= 41303

	periphFPLEETrayLegalPaper TRAP-TYPE
		ENTERPRISE	netPrinter
		DESCRIPTION
			"The peripheral is waiting for the operator 
			 to load paper of legal size in the
			 EE tray or envelope feeder."
	::= 41403

	periphFPLHCITray4LegalPaper TRAP-TYPE
		ENTERPRISE	netPrinter
		DESCRIPTION
			"The peripheral is waiting for the operator 
			 to load paper of legal size in hci tray 4."
	::= 41503

	periphFPLHCITray5LegalPaper TRAP-TYPE
		ENTERPRISE	netPrinter
		DESCRIPTION
			"The peripheral is waiting for the operator 
			 to load paper of legal size in hci tray 5."
	::= 41603

	periphFPLHCITray6LegalPaper TRAP-TYPE
		ENTERPRISE	netPrinter
		DESCRIPTION
			"The peripheral is waiting for the operator 
			 to load paper of legal size in hci tray 6."
	::= 41703

	periphFPLHCITray7LegalPaper TRAP-TYPE
		ENTERPRISE	netPrinter
		DESCRIPTION
			"The peripheral is waiting for the operator 
			 to load paper of legal size in hci tray 7."
	::= 41803

	periphFPLHCITray8orAllLegalPaper TRAP-TYPE
		ENTERPRISE	netPrinter
		DESCRIPTION
			"The peripheral is waiting for the operator 
			 to load paper of legal size in hci tray 8
			 or all input trays are out of paper."
	::= 41903


-- A4 paper  

	periphFPLMPTrayA4Paper TRAP-TYPE
		ENTERPRISE	netPrinter
		DESCRIPTION
			"The peripheral is waiting for the operator 
			 to load paper of A4 size in the
			 MP tray or envelope tray."
	::= 41004

	periphFPLManualFeedA4Paper TRAP-TYPE
		ENTERPRISE	netPrinter
		DESCRIPTION
			"The peripheral is waiting for the operator 
			 to load paper of A4 size in the
			 manual feed tray."
	::= 41104

	periphFPLPCTrayA4Paper TRAP-TYPE
		ENTERPRISE	netPrinter
		DESCRIPTION
			"The peripheral is waiting for the operator 
			 to load paper of A4 size in the
			 PC tray or universal tray 2."
	::= 41204

	periphFPLLCTrayA4Paper TRAP-TYPE
		ENTERPRISE	netPrinter
		DESCRIPTION
			"The peripheral is waiting for the operator 
			 to load paper of A4 size in the
			 LC tray or universal tray 3."
	::= 41304

	periphFPLEETrayA4Paper TRAP-TYPE
		ENTERPRISE	netPrinter
		DESCRIPTION
			"The peripheral is waiting for the operator 
			 to load paper of A4 size in the
			 EE tray or envelope feeder."
	::= 41404

	periphFPLHCITray4A4Paper TRAP-TYPE
		ENTERPRISE	netPrinter
		DESCRIPTION
			"The peripheral is waiting for the operator 
			 to load paper of A4 size in hci tray 4."
	::= 41504

	periphFPLHCITray5A4Paper TRAP-TYPE
		ENTERPRISE	netPrinter
		DESCRIPTION
			"The peripheral is waiting for the operator 
			 to load paper of A4 size in hci tray 5."
	::= 41604

	periphFPLHCITray6A4Paper TRAP-TYPE
		ENTERPRISE	netPrinter
		DESCRIPTION
			"The peripheral is waiting for the operator 
			 to load paper of A4 size in hci tray 6."
	::= 41704

	periphFPLHCITray7A4Paper TRAP-TYPE
		ENTERPRISE	netPrinter
		DESCRIPTION
			"The peripheral is waiting for the operator 
			 to load paper of A4 size in hci tray 7."
	::= 41804

	periphFPLHCITray8OrAllA4Paper TRAP-TYPE
		ENTERPRISE	netPrinter
		DESCRIPTION
			"The peripheral is waiting for the operator 
			 to load paper of A4 size in hci tray 8 or
			 all input trays are out of media."
	::= 41904


-- Executive paper  

	periphFPLMPTrayExecutivePaper TRAP-TYPE
		ENTERPRISE	netPrinter
		DESCRIPTION
			"The peripheral is waiting for the operator 
			 to load paper of Executive size in the
			 MP tray or envelope tray."
	::= 41005

	periphFPLManualFeedExecutivePaper TRAP-TYPE
		ENTERPRISE	netPrinter
		DESCRIPTION
			"The peripheral is waiting for the operator 
			 to load paper of Executive size in the
			 manual feed tray."
	::= 41105

	periphFPLPCTrayExecutivePaper TRAP-TYPE
		ENTERPRISE	netPrinter
		DESCRIPTION
			"The peripheral is waiting for the operator 
			 to load paper of Executive size in the
			 PC tray or universal tray 2."
	::= 41205

	periphFPLLCTrayExecutivePaper TRAP-TYPE
		ENTERPRISE	netPrinter
		DESCRIPTION
			"The peripheral is waiting for the operator 
			 to load paper of Executive size in the
			 LC tray or universal tray 3."
	::= 41305

	periphFPLEETrayExecutivePaper TRAP-TYPE
		ENTERPRISE	netPrinter
		DESCRIPTION
			"The peripheral is waiting for the operator 
			 to load paper of Executive size in the
			 EE tray or envelope feeder."
	::= 41405

	periphFPLHCITray4ExecutivePaper TRAP-TYPE
		ENTERPRISE	netPrinter
		DESCRIPTION
			"The peripheral is waiting for the operator 
			 to load paper of Executive size in hci tray 4."
	::= 41505

	periphFPLHCITray5ExecutivePaper TRAP-TYPE
		ENTERPRISE	netPrinter
		DESCRIPTION
			"The peripheral is waiting for the operator 
			 to load paper of Executive size in hci tray 5."
	::= 41605

	periphFPLHCITray6ExecutivePaper TRAP-TYPE
		ENTERPRISE	netPrinter
		DESCRIPTION
			"The peripheral is waiting for the operator 
			 to load paper of Executive size in hci tray 6."
	::= 41705

	periphFPLHCITray7ExecutivePaper TRAP-TYPE
		ENTERPRISE	netPrinter
		DESCRIPTION
			"The peripheral is waiting for the operator 
			 to load paper of Executive size in hci tray 7."
	::= 41805

	periphFPLHCITray8OrAllExecutivePaper TRAP-TYPE
		ENTERPRISE	netPrinter
		DESCRIPTION
			"The peripheral is waiting for the operator 
			 to load paper of Executive size in hci tray 8
			 or all input trays are out of media."
	::= 41905


-- Ledger paper  

	periphFPLMPTrayLedgerPaper TRAP-TYPE
		ENTERPRISE	netPrinter
		DESCRIPTION
			"The peripheral is waiting for the operator 
			 to load paper of Ledger size in the
			 MP tray or envelope tray."
	::= 41006

	periphFPLManualFeedLedgerPaper TRAP-TYPE
		ENTERPRISE	netPrinter
		DESCRIPTION
			"The peripheral is waiting for the operator 
			 to load paper of Ledger size in the
			 manual feed tray."
	::= 41106

	periphFPLPCTrayLedgerPaper TRAP-TYPE
		ENTERPRISE	netPrinter
		DESCRIPTION
			"The peripheral is waiting for the operator 
			 to load paper of Ledger size in the
			 PC tray or universal tray 2."
	::= 41206

	periphFPLLCTrayLedgerPaper TRAP-TYPE
		ENTERPRISE	netPrinter
		DESCRIPTION
			"The peripheral is waiting for the operator 
			 to load paper of Ledger size in the
			 LC tray or universal tray 3."
	::= 41306

	periphFPLEETrayLedgerPaper TRAP-TYPE
		ENTERPRISE	netPrinter
		DESCRIPTION
			"The peripheral is waiting for the operator 
			 to load paper of Ledger size in the
			 EE tray or envelope feeder."
	::= 41406

	periphFPLHCITray4LedgerPaper TRAP-TYPE
		ENTERPRISE	netPrinter
		DESCRIPTION
			"The peripheral is waiting for the operator 
			 to load paper of Ledger size in hci tray 4."
	::= 41506

	periphFPLHCITray5LedgerPaper TRAP-TYPE
		ENTERPRISE	netPrinter
		DESCRIPTION
			"The peripheral is waiting for the operator 
			 to load paper of Ledger size in hci tray 5."
	::= 41606

	periphFPLHCITray6LedgerPaper TRAP-TYPE
		ENTERPRISE	netPrinter
		DESCRIPTION
			"The peripheral is waiting for the operator 
			 to load paper of Ledger size in hci tray 6."
	::= 41706

	periphFPLHCITray7LedgerPaper TRAP-TYPE
		ENTERPRISE	netPrinter
		DESCRIPTION
			"The peripheral is waiting for the operator 
			 to load paper of Ledger size in hci tray 7."
	::= 41806

	periphFPLHCITray8OrAllLedgerPaper TRAP-TYPE
		ENTERPRISE	netPrinter
		DESCRIPTION
			"The peripheral is waiting for the operator 
			 to load paper of Ledger size in hci tray 8
			 or all input trays are out of media."
	::= 41906


-- A3 paper  

	periphFPLMPTrayA3Paper TRAP-TYPE
		ENTERPRISE	netPrinter
		DESCRIPTION
			"The peripheral is waiting for the operator 
			 to load paper of A3 size in the
			 MP tray or envelope tray."
	::= 41007

	periphFPLManualFeedA3Paper TRAP-TYPE
		ENTERPRISE	netPrinter
		DESCRIPTION
			"The peripheral is waiting for the operator 
			 to load paper of A3 size in the
			 manual feed tray."
	::= 41107

	periphFPLPCTrayA3Paper TRAP-TYPE
		ENTERPRISE	netPrinter
		DESCRIPTION
			"The peripheral is waiting for the operator 
			 to load paper of A3 size in the
			 PC tray or universal tray 2."
	::= 41207

	periphFPLLCTrayA3Paper TRAP-TYPE
		ENTERPRISE	netPrinter
		DESCRIPTION
			"The peripheral is waiting for the operator 
			 to load paper of A3 size in the
			 LC tray or universal tray 3."
	::= 41307

	periphFPLEETrayA3Paper TRAP-TYPE
		ENTERPRISE	netPrinter
		DESCRIPTION
			"The peripheral is waiting for the operator 
			 to load paper of A3 size in the
			 EE tray or envelope feeder."
	::= 41407

	periphFPLHCITray4A3Paper TRAP-TYPE
		ENTERPRISE	netPrinter
		DESCRIPTION
			"The peripheral is waiting for the operator 
			 to load paper of A3 size in hci tray 4."
	::= 41507

	periphFPLHCITray5A3Paper TRAP-TYPE
		ENTERPRISE	netPrinter
		DESCRIPTION
			"The peripheral is waiting for the operator 
			 to load paper of A3 size in hci tray 5."
	::= 41607

	periphFPLHCITray6A3Paper TRAP-TYPE
		ENTERPRISE	netPrinter
		DESCRIPTION
			"The peripheral is waiting for the operator 
			 to load paper of A3 size in hci tray 6."
	::= 41707

	periphFPLHCITray7A3Paper TRAP-TYPE
		ENTERPRISE	netPrinter
		DESCRIPTION
			"The peripheral is waiting for the operator 
			 to load paper of A3 size in hci tray 7."
	::= 41807

	periphFPLHCITray8OrAllA3Paper TRAP-TYPE
		ENTERPRISE	netPrinter
		DESCRIPTION
			"The peripheral is waiting for the operator 
			 to load paper of A3 size in hci tray 8
			 or all input trays are out of paper."
	::= 41907


-- COM10 envelope  

	periphFPLMPTrayCOM10Envelope TRAP-TYPE
		ENTERPRISE	netPrinter
		DESCRIPTION
			"The peripheral is waiting for the operator 
			 to load an envelope of an COM10 size in the
			 MP tray or envelope tray."
	::= 41008

	periphFPLManualFeedCOM10Envelope TRAP-TYPE
		ENTERPRISE	netPrinter
		DESCRIPTION
			"The peripheral is waiting for the operator 
			 to load an envelope of an COM10 size in the
			 manual feed tray."
	::= 41108

	periphFPLPCTrayCOM10Envelope TRAP-TYPE
		ENTERPRISE	netPrinter
		DESCRIPTION
			"The peripheral is waiting for the operator 
			 to load an envelope of an COM10 size in the
			 PC tray or universal tray 2."
	::= 41208

	periphFPLLCTrayCOM10Envelope TRAP-TYPE
		ENTERPRISE	netPrinter
		DESCRIPTION
			"The peripheral is waiting for the operator 
			 to load an envelope of an COM10 size in the
			 LC tray or universal tray 3."
	::= 41308

	periphFPLEETrayCOM10Envelope TRAP-TYPE
		ENTERPRISE	netPrinter
		DESCRIPTION
			"The peripheral is waiting for the operator 
			 to load an envelope of an COM10 size in the
			 EE tray or envelope feeder."
	::= 41408

	periphFPLHCITray4COM10Envelope TRAP-TYPE
		ENTERPRISE	netPrinter
		DESCRIPTION
			"The peripheral is waiting for the operator 
			 to load an envelope of an COM10 size in hci tray 4."
	::= 41508

	periphFPLHCITray5COM10Envelope TRAP-TYPE
		ENTERPRISE	netPrinter
		DESCRIPTION
			"The peripheral is waiting for the operator 
			 to load an envelope of an COM10 size in hci tray 5."
	::= 41608

	periphFPLHCITray6COM10Envelope TRAP-TYPE
		ENTERPRISE	netPrinter
		DESCRIPTION
			"The peripheral is waiting for the operator 
			 to load an envelope of an COM10 size in hci tray 6."
	::= 41708

	periphFPLHCITray7COM10Envelope TRAP-TYPE
		ENTERPRISE	netPrinter
		DESCRIPTION
			"The peripheral is waiting for the operator 
			 to load an envelope of an COM10 size in hci tray 7."
	::= 41808

	periphFPLHCITray8OrAllCOM10Envelope TRAP-TYPE
		ENTERPRISE	netPrinter
		DESCRIPTION
			"The peripheral is waiting for the operator 
			 to load an envelope of an COM10 size in hci tray 8
			 or all input trays are out of media."
	::= 41908


-- Monarch envelope  

	periphFPLMPTrayMonarchEnvelope TRAP-TYPE
		ENTERPRISE	netPrinter
		DESCRIPTION
			"The peripheral is waiting for the operator 
			 to load an envelope of an Monarch size in the
			 MP tray or envelope tray."
	::= 41009

	periphFPLManualFeedMonarchEnvelope TRAP-TYPE
		ENTERPRISE	netPrinter
		DESCRIPTION
			"The peripheral is waiting for the operator 
			 to load an envelope of an Monarch size in the
			 manual feed tray."
	::= 41109

	periphFPLPCTrayMonarchEnvelope TRAP-TYPE
		ENTERPRISE	netPrinter
		DESCRIPTION
			"The peripheral is waiting for the operator 
			 to load an envelope of an Monarch size in the
			 PC tray or universal tray 2."
	::= 41209

	periphFPLLCTrayMonarchEnvelope TRAP-TYPE
		ENTERPRISE	netPrinter
		DESCRIPTION
			"The peripheral is waiting for the operator 
			 to load an envelope of an Monarch size in the
			 LC tray or universal tray 3."
	::= 41309

	periphFPLEETrayMonarchEnvelope TRAP-TYPE
		ENTERPRISE	netPrinter
		DESCRIPTION
			"The peripheral is waiting for the operator 
			 to load an envelope of an Monarch size in the
			 EE tray or envelope feeder."
	::= 41409

	periphFPLHCITray4MonarchEnvelope TRAP-TYPE
		ENTERPRISE	netPrinter
		DESCRIPTION
			"The peripheral is waiting for the operator 
			 to load an envelope of an Monarch size in hci tray 4."
	::= 41509

	periphFPLHCITray5MonarchEnvelope TRAP-TYPE
		ENTERPRISE	netPrinter
		DESCRIPTION
			"The peripheral is waiting for the operator 
			 to load an envelope of an Monarch size in hci tray 5."
	::= 41609

	periphFPLHCITray6MonarchEnvelope TRAP-TYPE
		ENTERPRISE	netPrinter
		DESCRIPTION
			"The peripheral is waiting for the operator 
			 to load an envelope of an Monarch size in hci tray 6."
	::= 41709

	periphFPLHCITray7MonarchEnvelope TRAP-TYPE
		ENTERPRISE	netPrinter
		DESCRIPTION
			"The peripheral is waiting for the operator 
			 to load an envelope of an Monarch size in hci tray ."
	::= 41809

	periphFPLHCITray8OrAllMonarchEnvelope TRAP-TYPE
		ENTERPRISE	netPrinter
		DESCRIPTION
			"The peripheral is waiting for the operator 
			 to load an envelope of an Monarch size in hci tray 8
			 or all input trays are out of media."
	::= 41909


-- C5 envelope  

	periphFPLMPTrayC5Envelope TRAP-TYPE
		ENTERPRISE	netPrinter
		DESCRIPTION
			"The peripheral is waiting for the operator 
			 to load an envelope of an C5 size in the
			 MP tray or envelope tray."
	::= 41010

	periphFPLManualFeedC5Envelope TRAP-TYPE
		ENTERPRISE	netPrinter
		DESCRIPTION
			"The peripheral is waiting for the operator 
			 to load an envelope of an C5 size in the
			 manual feed tray."
	::= 41110

	periphFPLPCTrayC5Envelope TRAP-TYPE
		ENTERPRISE	netPrinter
		DESCRIPTION
			"The peripheral is waiting for the operator 
			 to load an envelope of an C5 size in the
			 PC tray or universal tray 2."
	::= 41210

	periphFPLLCTrayC5Envelope TRAP-TYPE
		ENTERPRISE	netPrinter
		DESCRIPTION
			"The peripheral is waiting for the operator 
			 to load an envelope of an C5 size in the
			 LC tray or universal tray 3."
	::= 41310

	periphFPLEETrayC5Envelope TRAP-TYPE
		ENTERPRISE	netPrinter
		DESCRIPTION
			"The peripheral is waiting for the operator 
			 to load an envelope of an C5 size in the
			 EE tray or envelope feeder."
	::= 41410

	periphFPLHCITray4C5Envelope TRAP-TYPE
		ENTERPRISE	netPrinter
		DESCRIPTION
			"The peripheral is waiting for the operator 
			 to load an envelope of an C5 size in hci tray 4."
	::= 41510

	periphFPLHCITray5C5Envelope TRAP-TYPE
		ENTERPRISE	netPrinter
		DESCRIPTION
			"The peripheral is waiting for the operator 
			 to load an envelope of an C5 size in hci tray 5."
	::= 41610

	periphFPLHCITray6C5Envelope TRAP-TYPE
		ENTERPRISE	netPrinter
		DESCRIPTION
			"The peripheral is waiting for the operator 
			 to load an envelope of an C5 size in hci tray 6."
	::= 41710

	periphFPLHCITray7C5Envelope TRAP-TYPE
		ENTERPRISE	netPrinter
		DESCRIPTION
			"The peripheral is waiting for the operator 
			 to load an envelope of an C5 size in hci tray 7."
	::= 41810

	periphFPLHCITray8OrAllC5Envelope TRAP-TYPE
		ENTERPRISE	netPrinter
		DESCRIPTION
			"The peripheral is waiting for the operator 
			 to load an envelope of an C5 size in hci tray 8
			 or all input trays are out of media."
	::= 41910


-- DL envelope  

	periphFPLMPTrayDLEnvelope TRAP-TYPE
		ENTERPRISE	netPrinter
		DESCRIPTION
			"The peripheral is waiting for the operator 
			 to load an envelope of an DL size in the
			 MP tray or envelope tray."
	::= 41011

	periphFPLManualFeedDLEnvelope TRAP-TYPE
		ENTERPRISE	netPrinter
		DESCRIPTION
			"The peripheral is waiting for the operator 
			 to load an envelope of an DL size in the
			 manual feed tray."
	::= 41111

	periphFPLPCTrayDLEnvelope TRAP-TYPE
		ENTERPRISE	netPrinter
		DESCRIPTION
			"The peripheral is waiting for the operator 
			 to load an envelope of an DL size in the
			 PC tray or universal tray 2."
	::= 41211

	periphFPLLCTrayDLEnvelope TRAP-TYPE
		ENTERPRISE	netPrinter
		DESCRIPTION
			"The peripheral is waiting for the operator 
			 to load an envelope of an DL size in the
			 LC tray or universal tray 3."
	::= 41311

	periphFPLEETrayDLEnvelope TRAP-TYPE
		ENTERPRISE	netPrinter
		DESCRIPTION
			"The peripheral is waiting for the operator 
			 to load an envelope of an DL size in the
			 EE tray or envelope feeder."
	::= 41411

	periphFPLHCITray4DLEnvelope TRAP-TYPE
		ENTERPRISE	netPrinter
		DESCRIPTION
			"The peripheral is waiting for the operator 
			 to load an envelope of an DL size in hci tray 4."
	::= 41511

	periphFPLHCITray5DLEnvelope TRAP-TYPE
		ENTERPRISE	netPrinter
		DESCRIPTION
			"The peripheral is waiting for the operator 
			 to load an envelope of an DL size in hci tray 5."
	::= 41611

	periphFPLHCITray6DLEnvelope TRAP-TYPE
		ENTERPRISE	netPrinter
		DESCRIPTION
			"The peripheral is waiting for the operator 
			 to load an envelope of an DL size in hci tray 6."
	::= 41711

	periphFPLHCITray7DLEnvelope TRAP-TYPE
		ENTERPRISE	netPrinter
		DESCRIPTION
			"The peripheral is waiting for the operator 
			 to load an envelope of an DL size in hci tray 7."
	::= 41811

	periphFPLHCITray8OrAllDLEnvelope TRAP-TYPE
		ENTERPRISE	netPrinter
		DESCRIPTION
			"The peripheral is waiting for the operator 
			 to load an envelope of an DL size in hci tray 8
			 or all input trays are out of media."
	::= 41911


-- JISB4 paper  

	periphFPLMPTrayJISB4Paper TRAP-TYPE
		ENTERPRISE	netPrinter
		DESCRIPTION
			"The peripheral is waiting for the operator 
			 to load paper of JISB4 size in the
			 MP tray or envelope tray."
	::= 41012

	periphFPLManualFeedJISB4Paper TRAP-TYPE
		ENTERPRISE	netPrinter
		DESCRIPTION
			"The peripheral is waiting for the operator 
			 to load paper of JISB4 size in the
			 manual feed tray."
	::= 41112

	periphFPLPCTrayJISB4Paper TRAP-TYPE
		ENTERPRISE	netPrinter
		DESCRIPTION
			"The peripheral is waiting for the operator 
			 to load paper of JISB4 size in the
			 PC tray or universal tray 2."
	::= 41212

	periphFPLLCTrayJISB4Paper TRAP-TYPE
		ENTERPRISE	netPrinter
		DESCRIPTION
			"The peripheral is waiting for the operator 
			 to load paper of JISB4 size in the
			 LC tray or universal tray 3."
	::= 41312

	periphFPLEETrayJISB4Paper TRAP-TYPE
		ENTERPRISE	netPrinter
		DESCRIPTION
			"The peripheral is waiting for the operator 
			 to load paper of JISB4 size in the
			 EE tray or envelope feeder."
	::= 41412

	periphFPLHCITray4JISB4Paper TRAP-TYPE
		ENTERPRISE	netPrinter
		DESCRIPTION
			"The peripheral is waiting for the operator 
			 to load paper of JISB4 size in hci tray 4."
	::= 41512

	periphFPLHCITray5JISB4Paper TRAP-TYPE
		ENTERPRISE	netPrinter
		DESCRIPTION
			"The peripheral is waiting for the operator 
			 to load paper of JISB4 size in hci tray 5."
	::= 41612

	periphFPLHCITray6JISB4Paper TRAP-TYPE
		ENTERPRISE	netPrinter
		DESCRIPTION
			"The peripheral is waiting for the operator 
			 to load paper of JISB4 size in hci tray 6."
	::= 41712

	periphFPLHCITray7JISB4Paper TRAP-TYPE
		ENTERPRISE	netPrinter
		DESCRIPTION
			"The peripheral is waiting for the operator 
			 to load paper of JISB4 size in hci tray 7."
	::= 41812

	periphFPLHCITray8OrAllJISB4Paper TRAP-TYPE
		ENTERPRISE	netPrinter
		DESCRIPTION
			"The peripheral is waiting for the operator 
			 to load paper of JISB4 size in hci tray 8
			 or all input trays are out of media."
	::= 41912


-- JISB5 paper  

	periphFPLMPTrayJISB5Paper TRAP-TYPE
		ENTERPRISE	netPrinter
		DESCRIPTION
			"The peripheral is waiting for the operator 
			 to load paper of JISB5 size in the
			 MP tray or envelope tray."
	::= 41013

	periphFPLManualFeedJISB5Paper TRAP-TYPE
		ENTERPRISE	netPrinter
		DESCRIPTION
			"The peripheral is waiting for the operator 
			 to load paper of JISB5 size in the
			 manual feed tray."
	::= 41113

	periphFPLPCTrayJISB5Paper TRAP-TYPE
		ENTERPRISE	netPrinter
		DESCRIPTION
			"The peripheral is waiting for the operator 
			 to load paper of JISB5 size in the
			 PC tray or universal tray 2."
	::= 41213

	periphFPLLCTrayJISB5Paper TRAP-TYPE
		ENTERPRISE	netPrinter
		DESCRIPTION
			"The peripheral is waiting for the operator 
			 to load paper of JISB5 size in the
			 LC tray or universal tray 3."
	::= 41313

	periphFPLEETrayJISB5Paper TRAP-TYPE
		ENTERPRISE	netPrinter
		DESCRIPTION
			"The peripheral is waiting for the operator 
			 to load paper of JISB5 size in the
			 EE tray or envelope feeder."
	::= 41413

	periphFPLHCITray4JISB5Paper TRAP-TYPE
		ENTERPRISE	netPrinter
		DESCRIPTION
			"The peripheral is waiting for the operator 
			 to load paper of JISB5 size in hci tray 4."
	::= 41513

	periphFPLHCITray5JISB5Paper TRAP-TYPE
		ENTERPRISE	netPrinter
		DESCRIPTION
			"The peripheral is waiting for the operator 
			 to load paper of JISB5 size in hci tray 5."
	::= 41613

	periphFPLHCITray6JISB5Paper TRAP-TYPE
		ENTERPRISE	netPrinter
		DESCRIPTION
			"The peripheral is waiting for the operator 
			 to load paper of JISB5 size in hci tray 6."
	::= 41713

	periphFPLHCITray7JISB5Paper TRAP-TYPE
		ENTERPRISE	netPrinter
		DESCRIPTION
			"The peripheral is waiting for the operator 
			 to load paper of JISB5 size in hci tray 7."
	::= 41813

	periphFPLHCITray8OrAllJISB5Paper TRAP-TYPE
		ENTERPRISE	netPrinter
		DESCRIPTION
			"The peripheral is waiting for the operator 
			 to load paper of JISB5 size in hci tray 8
			 or all input trays are out of media."
	::= 41913


-- InternationalB5 envelope  

	periphFPLMPTrayInternationalB5Envelope TRAP-TYPE
		ENTERPRISE	netPrinter
		DESCRIPTION
			"The peripheral is waiting for the operator 
			 to load an envelope of an International B5 size in the
			 MP tray or envelope tray."
	::= 41014

	periphFPLManualFeedInternationalB5Envelope TRAP-TYPE
		ENTERPRISE	netPrinter
		DESCRIPTION
			"The peripheral is waiting for the operator 
			 to load an envelope of an International B5 size in the
			 manual feed tray."
	::= 41114

	periphFPLPCTrayInternationalB5Envelope TRAP-TYPE
		ENTERPRISE	netPrinter
		DESCRIPTION
			"The peripheral is waiting for the operator 
			 to load an envelope of an International B5 size in the
			 PC tray or universal tray 2."
	::= 41214

	periphFPLLCTrayInternationalB5Envelope TRAP-TYPE
		ENTERPRISE	netPrinter
		DESCRIPTION
			"The peripheral is waiting for the operator 
			 to load an envelope of an International B5 size in the
			 LC tray or universal tray 3."
	::= 41314

	periphFPLEETrayInternationalB5Envelope TRAP-TYPE
		ENTERPRISE	netPrinter
		DESCRIPTION
			"The peripheral is waiting for the operator 
			 to load an envelope of an International B5 size in the
			 EE tray or envelope feeder."
	::= 41414

	periphFPLHCITray4InternationalB5Envelope TRAP-TYPE
		ENTERPRISE	netPrinter
		DESCRIPTION
			"The peripheral is waiting for the operator 
			 to load an envelope of an International B5 size in 
			 hci tray 4."
	::= 41514

	periphFPLHCITray5InternationalB5Envelope TRAP-TYPE
		ENTERPRISE	netPrinter
		DESCRIPTION
			"The peripheral is waiting for the operator 
			 to load an envelope of an International B5 size in 
			 hci tray 5."
	::= 41614

	periphFPLHCITray6InternationalB5Envelope TRAP-TYPE
		ENTERPRISE	netPrinter
		DESCRIPTION
			"The peripheral is waiting for the operator 
			 to load an envelope of an International B5 size in 
			 hci tray 6."
	::= 41714

	periphFPLHCITray7InternationalB5Envelope TRAP-TYPE
		ENTERPRISE	netPrinter
		DESCRIPTION
			"The peripheral is waiting for the operator 
			 to load an envelope of an International B5 size in 
			 hci tray 7."
	::= 41814

	periphFPLHCITray8InternationalB5Envelope TRAP-TYPE
		ENTERPRISE	netPrinter
		DESCRIPTION
			"The peripheral is waiting for the operator 
			 to load an envelope of an International B5 size in 
			 hci tray 8."
	::= 41914



-- Custom Media  

	periphFPLMPTrayCustomMedia TRAP-TYPE
		ENTERPRISE	netPrinter
		DESCRIPTION
			"The peripheral is waiting for the operator 
			 to load paper of Custom size in the
			 MP tray or envelope tray."
	::= 41015

	periphFPLManualFeedCustomMedia TRAP-TYPE
		ENTERPRISE	netPrinter
		DESCRIPTION
			"The peripheral is waiting for the operator 
			 to load paper of Custom size in the
			 manual feed tray."
	::= 41115

	periphFPLPCTrayCustomMedia TRAP-TYPE
		ENTERPRISE	netPrinter
		DESCRIPTION
			"The peripheral is waiting for the operator 
			 to load paper of Custom size in the
			 PC tray or universal tray 2."
	::= 41215

	periphFPLLCTrayCustomMedia TRAP-TYPE
		ENTERPRISE	netPrinter
		DESCRIPTION
			"The peripheral is waiting for the operator 
			 to load paper of Custom size in the
			 LC tray or universal tray 3."
	::= 41315

	periphFPLEETrayCustomMedia TRAP-TYPE
		ENTERPRISE	netPrinter
		DESCRIPTION
			"The peripheral is waiting for the operator 
			 to load paper of Custom size in the
			 EE tray or envelope feeder."
	::= 41415

	periphFPLHCITray4CustomMedia TRAP-TYPE
		ENTERPRISE	netPrinter
		DESCRIPTION
			"The peripheral is waiting for the operator 
			 to load paper of Custom size in hci tray 4."
	::= 41515

	periphFPLHCITray5CustomMedia TRAP-TYPE
		ENTERPRISE	netPrinter
		DESCRIPTION
			"The peripheral is waiting for the operator 
			 to load paper of Custom size in hci tray 5."
	::= 41615

	periphFPLHCITray6CustomMedia TRAP-TYPE
		ENTERPRISE	netPrinter
		DESCRIPTION
			"The peripheral is waiting for the operator 
			 to load paper of Custom size in hci tray 6."
	::= 41715

	periphFPLHCITray7CustomMedia TRAP-TYPE
		ENTERPRISE	netPrinter
		DESCRIPTION
			"The peripheral is waiting for the operator 
			 to load paper of Custom size in hci tray 7."
	::= 41815

	periphFPLHCITray8OrAllCustomMedia TRAP-TYPE
		ENTERPRISE	netPrinter
		DESCRIPTION
			"The peripheral is waiting for the operator 
			 to load paper of Custom size in hci tray 8
			 or all input trays are out of media."
	::= 41915


-- Japanese Postcard

	periphFPLMPTrayJapanesePostcard TRAP-TYPE
		ENTERPRISE	netPrinter
		DESCRIPTION
			"The peripheral is waiting for the operator 
			 to load media of Japanese Postcard size in the
			 MP tray or envelope tray."
	::= 41016

	periphFPLManualFeedJapanesePostcard TRAP-TYPE
		ENTERPRISE	netPrinter
		DESCRIPTION
			"The peripheral is waiting for the operator 
			 to load media of japanese postcard size in the
			 manual feed tray."
	::= 41116

	periphFPLPCTrayJapanesePostcard TRAP-TYPE
		ENTERPRISE	netPrinter
		DESCRIPTION
			"The peripheral is waiting for the operator 
			 to load media of japanese postcard size in the
			 PC tray or universal tray 2."
	::= 41216

	periphFPLLCTrayJapanesePostcard TRAP-TYPE
		ENTERPRISE	netPrinter
		DESCRIPTION
			"The peripheral is waiting for the operator 
			 to load media of japanese postcard size in the
			 LC tray or universal tray 3."
	::= 41316

	periphFPLEETrayJapanesePostcard TRAP-TYPE
		ENTERPRISE	netPrinter
		DESCRIPTION
			"The peripheral is waiting for the operator 
			 to load media of japanese postcard size in the
			 EE tray or envelope feeder."
	::= 41416

	periphFPLHCITray4JapanesePostcard TRAP-TYPE
		ENTERPRISE	netPrinter
		DESCRIPTION
			"The peripheral is waiting for the operator 
			 to load media of japanese postcard size in hci tray 4."
	::= 41516

	periphFPLHCITray5JapanesePostcard TRAP-TYPE
		ENTERPRISE	netPrinter
		DESCRIPTION
			"The peripheral is waiting for the operator 
			 to load media of japanese postcard size in hci tray 5."
	::= 41616

	periphFPLHCITray6JapanesePostcard TRAP-TYPE
		ENTERPRISE	netPrinter
		DESCRIPTION
			"The peripheral is waiting for the operator 
			 to load media of japanese postcard size in hci tray 6."
	::= 41716

	periphFPLHCITray7JapanesePostcard TRAP-TYPE
		ENTERPRISE	netPrinter
		DESCRIPTION
			"The peripheral is waiting for the operator 
			 to load media of japanese postcard size in hci tray 7."
	::= 41816

	periphFPLHCITray8OrAllJapanesePostcard TRAP-TYPE
		ENTERPRISE	netPrinter
		DESCRIPTION
			"The peripheral is waiting for the operator 
			 to load media of japanese postcard size in hci tray 8
			 or all input trays are out of media."
	::= 41916

-- Japanese RTPostcard

	periphFPLMPTrayJapaneseRTPostcard TRAP-TYPE
		ENTERPRISE	netPrinter
		DESCRIPTION
			"The peripheral is waiting for the operator 
			 to load media of Japanese RTPostcard size in the
			 MP tray or envelope tray."
	::= 41017

	periphFPLManualFeedJapaneseRTPostcard TRAP-TYPE
		ENTERPRISE	netPrinter
		DESCRIPTION
			"The peripheral is waiting for the operator 
			 to load media of japanese RTPostcard size in the
			 manual feed tray."
	::= 41117

	periphFPLPCTrayJapaneseRTPostcard TRAP-TYPE
		ENTERPRISE	netPrinter
		DESCRIPTION
			"The peripheral is waiting for the operator 
			 to load media of japanese RTPostcard size in the
			 PC tray or universal tray 2."
	::= 41217

	periphFPLLCTrayJapaneseRTPostcard TRAP-TYPE
		ENTERPRISE	netPrinter
		DESCRIPTION
			"The peripheral is waiting for the operator 
			 to load media of japanese RTPostcard size in the
			 LC tray or universal tray 3."
	::= 41317

	periphFPLEETrayJapaneseRTPostcard TRAP-TYPE
		ENTERPRISE	netPrinter
		DESCRIPTION
			"The peripheral is waiting for the operator 
			 to load media of japanese RTPostcard size in the
			 EE tray or envelope feeder."
	::= 41417

	periphFPLHCITray4JapaneseRTPostcard TRAP-TYPE
		ENTERPRISE	netPrinter
		DESCRIPTION
			"The peripheral is waiting for the operator 
			 to load media of japanese RTPostcard size in hci tray 4."
	::= 41517

	periphFPLHCITray5JapaneseRTPostcard TRAP-TYPE
		ENTERPRISE	netPrinter
		DESCRIPTION
			"The peripheral is waiting for the operator 
			 to load media of japanese RTPostcard size in hci tray 5."
	::= 41617

	periphFPLHCITray6JapaneseRTPostcard TRAP-TYPE
		ENTERPRISE	netPrinter
		DESCRIPTION
			"The peripheral is waiting for the operator 
			 to load media of japanese RTPostcard size in hci tray 6."
	::= 41717

	periphFPLHCITray7JapaneseRTPostcard TRAP-TYPE
		ENTERPRISE	netPrinter
		DESCRIPTION
			"The peripheral is waiting for the operator 
			 to load media of japanese RTPostcard size in hci tray 7."
	::= 41817

	periphFPLHCITray8OrAllJapaneseRTPostcard TRAP-TYPE
		ENTERPRISE	netPrinter
		DESCRIPTION
			"The peripheral is waiting for the operator 
			 to load media of japanese RTPostcard size in hci tray 8
			 or all input trays are out of media."
	::= 41917

-- A5 Paper

	periphFPLMPTrayA5Paper TRAP-TYPE
		ENTERPRISE	netPrinter
		DESCRIPTION
			"The peripheral is waiting for the operator 
			 to load media of A5 size in the
			 MP tray or envelope tray."
	::= 41018

	periphFPLManualFeedA5Paper TRAP-TYPE
		ENTERPRISE	netPrinter
		DESCRIPTION
			"The peripheral is waiting for the operator 
			 to load media of A5 size in the
			 manual feed tray."
	::= 41118

	periphFPLPCTrayA5Paper TRAP-TYPE
		ENTERPRISE	netPrinter
		DESCRIPTION
			"The peripheral is waiting for the operator 
			 to load media of A5 size in the
			 PC tray or universal tray 2."
	::= 41218

	periphFPLLCTrayA5Paper TRAP-TYPE
		ENTERPRISE	netPrinter
		DESCRIPTION
			"The peripheral is waiting for the operator 
			 to load media of A5 size in the
			 LC tray or universal tray 3."
	::= 41318

	periphFPLEETrayA5Paper TRAP-TYPE
		ENTERPRISE	netPrinter
		DESCRIPTION
			"The peripheral is waiting for the operator 
			 to load media of A5 size in the
			 EE tray or envelope feeder."
	::= 41418

	periphFPLHCITray4A5Paper TRAP-TYPE
		ENTERPRISE	netPrinter
		DESCRIPTION
			"The peripheral is waiting for the operator 
			 to load media of A5 size in hci tray 4."
	::= 41518

	periphFPLHCITray5A5Paper TRAP-TYPE
		ENTERPRISE	netPrinter
		DESCRIPTION
			"The peripheral is waiting for the operator 
			 to load media of A5 size in hci tray 5."
	::= 41618

	periphFPLHCITray6A5Paper TRAP-TYPE
		ENTERPRISE	netPrinter
		DESCRIPTION
			"The peripheral is waiting for the operator 
			 to load media of A5 size in hci tray 6."
	::= 41718

	periphFPLHCITray7A5Paper TRAP-TYPE
		ENTERPRISE	netPrinter
		DESCRIPTION
			"The peripheral is waiting for the operator 
			 to load media of A5 size in hci tray 7."
	::= 41818

	periphFPLHCITray8OrAllA5Paper TRAP-TYPE
		ENTERPRISE	netPrinter
		DESCRIPTION
			"The peripheral is waiting for the operator 
			 to load media of A5 size in hci tray 8
			 or all input trays are out of media."
	::= 41918

-- Letter-R Paper

	periphFPLMPTrayLetterRPaper TRAP-TYPE
		ENTERPRISE	netPrinter
		DESCRIPTION
			"The peripheral is waiting for the operator 
			 to load media of Letter-R size in the
			 MP tray or envelope tray."
	::= 41019

	periphFPLManualFeedLetterRPaper TRAP-TYPE
		ENTERPRISE	netPrinter
		DESCRIPTION
			"The peripheral is waiting for the operator 
			 to load media of Letter-R size in the
			 manual feed tray."
	::= 41119

	periphFPLPCTrayLetterRPaper TRAP-TYPE
		ENTERPRISE	netPrinter
		DESCRIPTION
			"The peripheral is waiting for the operator 
			 to load media of Letter-R size in the
			 PC tray or universal tray 2."
	::= 41219

	periphFPLLCTrayLetterRPaper TRAP-TYPE
		ENTERPRISE	netPrinter
		DESCRIPTION
			"The peripheral is waiting for the operator 
			 to load media of Letter-R size in the
			 LC tray or universal tray 3."
	::= 41319

	periphFPLEETrayLetterRPaper TRAP-TYPE
		ENTERPRISE	netPrinter
		DESCRIPTION
			"The peripheral is waiting for the operator 
			 to load media of Letter-R size in the
			 EE tray or envelope feeder."
	::= 41419

	periphFPLHCITray4LetterRPaper TRAP-TYPE
		ENTERPRISE	netPrinter
		DESCRIPTION
			"The peripheral is waiting for the operator 
			 to load media of Letter-R size in hci tray 4."
	::= 41519

	periphFPLHCITray5LetterRPaper TRAP-TYPE
		ENTERPRISE	netPrinter
		DESCRIPTION
			"The peripheral is waiting for the operator 
			 to load media of Letter-R size in hci tray 5."
	::= 41619

	periphFPLHCITray6LetterRPaper TRAP-TYPE
		ENTERPRISE	netPrinter
		DESCRIPTION
			"The peripheral is waiting for the operator 
			 to load media of Letter-R size in hci tray 6."
	::= 41719

	periphFPLHCITray7LetterRPaper TRAP-TYPE
		ENTERPRISE	netPrinter
		DESCRIPTION
			"The peripheral is waiting for the operator 
			 to load media of Letter-R size in hci tray 7."
	::= 41819

	periphFPLHCITray8OrAllLetterRPaper TRAP-TYPE
		ENTERPRISE	netPrinter
		DESCRIPTION
			"The peripheral is waiting for the operator 
			 to load media of Letter-R size in hci tray 8
			 or all input trays are out of media."
	::= 41919

-- A4-R Paper

	periphFPLMPTrayA4RPaper TRAP-TYPE
		ENTERPRISE	netPrinter
		DESCRIPTION
			"The peripheral is waiting for the operator 
			 to load media of A4-R size in the
			 MP tray or envelope tray."
	::= 41020

	periphFPLManualFeedA4RPaper TRAP-TYPE
		ENTERPRISE	netPrinter
		DESCRIPTION
			"The peripheral is waiting for the operator 
			 to load media of A4-R size in the
			 manual feed tray."
	::= 41120

	periphFPLPCTrayA4RPaper TRAP-TYPE
		ENTERPRISE	netPrinter
		DESCRIPTION
			"The peripheral is waiting for the operator 
			 to load media of A4-R size in the
			 PC tray or universal tray 2."
	::= 41220

	periphFPLLCTrayA4RPaper TRAP-TYPE
		ENTERPRISE	netPrinter
		DESCRIPTION
			"The peripheral is waiting for the operator 
			 to load media of A4-R size in the
			 LC tray or universal tray 3."
	::= 41320

	periphFPLEETrayA4RPaper TRAP-TYPE
		ENTERPRISE	netPrinter
		DESCRIPTION
			"The peripheral is waiting for the operator 
			 to load media of A4-R size in the
			 EE tray or envelope feeder."
	::= 41420

	periphFPLHCITray4A4RPaper TRAP-TYPE
		ENTERPRISE	netPrinter
		DESCRIPTION
			"The peripheral is waiting for the operator 
			 to load media of A4-R size in hci tray 4."
	::= 41520

	periphFPLHCITray5A4RPaper TRAP-TYPE
		ENTERPRISE	netPrinter
		DESCRIPTION
			"The peripheral is waiting for the operator 
			 to load media of A4-R size in hci tray 5."
	::= 41620

	periphFPLHCITray6A4RPaper TRAP-TYPE
		ENTERPRISE	netPrinter
		DESCRIPTION
			"The peripheral is waiting for the operator 
			 to load media of A4-R size in hci tray 6."
	::= 41720

	periphFPLHCITray7A4RPaper TRAP-TYPE
		ENTERPRISE	netPrinter
		DESCRIPTION
			"The peripheral is waiting for the operator 
			 to load media of A4-R size in hci tray 7."
	::= 41820

	periphFPLHCITray8OrAllA4RPaper TRAP-TYPE
		ENTERPRISE	netPrinter
		DESCRIPTION
			"The peripheral is waiting for the operator 
			 to load media of A4-R size in hci tray 8
			 or all input trays are out of media."
	::= 41920

-- A5-R Paper

	periphFPLMPTrayA5RPaper TRAP-TYPE
		ENTERPRISE	netPrinter
		DESCRIPTION
			"The peripheral is waiting for the operator 
			 to load media of A5-R size in the
			 MP tray or envelope tray."
	::= 41021

	periphFPLManualFeedA5RPaper TRAP-TYPE
		ENTERPRISE	netPrinter
		DESCRIPTION
			"The peripheral is waiting for the operator 
			 to load media of A5-R size in the
			 manual feed tray."
	::= 41121

	periphFPLPCTrayA5RPaper TRAP-TYPE
		ENTERPRISE	netPrinter
		DESCRIPTION
			"The peripheral is waiting for the operator 
			 to load media of A5-R size in the
			 PC tray or universal tray 2."
	::= 41221

	periphFPLLCTrayA5RPaper TRAP-TYPE
		ENTERPRISE	netPrinter
		DESCRIPTION
			"The peripheral is waiting for the operator 
			 to load media of A5-R size in the
			 LC tray or universal tray 3."
	::= 41321

	periphFPLEETrayA5RPaper TRAP-TYPE
		ENTERPRISE	netPrinter
		DESCRIPTION
			"The peripheral is waiting for the operator 
			 to load media of A5-R size in the
			 EE tray or envelope feeder."
	::= 41421

	periphFPLHCITray4A5RPaper TRAP-TYPE
		ENTERPRISE	netPrinter
		DESCRIPTION
			"The peripheral is waiting for the operator 
			 to load media of A5-R size in hci tray 4."
	::= 41521

	periphFPLHCITray5A5RPaper TRAP-TYPE
		ENTERPRISE	netPrinter
		DESCRIPTION
			"The peripheral is waiting for the operator 
			 to load media of A5-R size in hci tray 5."
	::= 41621

	periphFPLHCITray6A5RPaper TRAP-TYPE
		ENTERPRISE	netPrinter
		DESCRIPTION
			"The peripheral is waiting for the operator 
			 to load media of A5-R size in hci tray 6."
	::= 41721

	periphFPLHCITray7A5RPaper TRAP-TYPE
		ENTERPRISE	netPrinter
		DESCRIPTION
			"The peripheral is waiting for the operator 
			 to load media of A5-R size in hci tray 7."
	::= 41821

	periphFPLHCITray8OrAllA5RPaper TRAP-TYPE
		ENTERPRISE	netPrinter
		DESCRIPTION
			"The peripheral is waiting for the operator 
			 to load media of A5-R size in hci tray 8
			 or all input trays are out of media."
	::= 41921

-- B5-R Paper

	periphFPLMPTrayB5RPaper TRAP-TYPE
		ENTERPRISE	netPrinter
		DESCRIPTION
			"The peripheral is waiting for the operator 
			 to load media of B5-R size in the
			 MP tray or envelope tray."
	::= 41022

	periphFPLManualFeedB5RPaper TRAP-TYPE
		ENTERPRISE	netPrinter
		DESCRIPTION
			"The peripheral is waiting for the operator 
			 to load media of B5-R size in the
			 manual feed tray."
	::= 41122

	periphFPLPCTrayB5RPaper TRAP-TYPE
		ENTERPRISE	netPrinter
		DESCRIPTION
			"The peripheral is waiting for the operator 
			 to load media of B5-R size in the
			 PC tray or universal tray 2."
	::= 41222

	periphFPLLCTrayB5RPaper TRAP-TYPE
		ENTERPRISE	netPrinter
		DESCRIPTION
			"The peripheral is waiting for the operator 
			 to load media of B5-R size in the
			 LC tray or universal tray 3."
	::= 41322

	periphFPLEETrayB5RPaper TRAP-TYPE
		ENTERPRISE	netPrinter
		DESCRIPTION
			"The peripheral is waiting for the operator 
			 to load media of B5-R size in the
			 EE tray or envelope feeder."
	::= 41422

	periphFPLHCITray4B5RPaper TRAP-TYPE
		ENTERPRISE	netPrinter
		DESCRIPTION
			"The peripheral is waiting for the operator 
			 to load media of B5-R size in hci tray 4."
	::= 41522

	periphFPLHCITray5B5RPaper TRAP-TYPE
		ENTERPRISE	netPrinter
		DESCRIPTION
			"The peripheral is waiting for the operator 
			 to load media of B5-R size in hci tray 5."
	::= 41622

	periphFPLHCITray6B5RPaper TRAP-TYPE
		ENTERPRISE	netPrinter
		DESCRIPTION
			"The peripheral is waiting for the operator 
			 to load media of B5-R size in hci tray 6."
	::= 41722

	periphFPLHCITray7B5RPaper TRAP-TYPE
		ENTERPRISE	netPrinter
		DESCRIPTION
			"The peripheral is waiting for the operator 
			 to load media of B5-R size in hci tray 7."
	::= 41822

	periphFPLHCITray8OrAllB5RPaper TRAP-TYPE
		ENTERPRISE	netPrinter
		DESCRIPTION
			"The peripheral is waiting for the operator 
			 to load media of B5-R size in hci tray 8
			 or all input trays are out of media."
	::= 41922

-- Executive-R Paper

	periphFPLMPTrayExecutiveRPaper TRAP-TYPE
		ENTERPRISE	netPrinter
		DESCRIPTION
			"The peripheral is waiting for the operator 
			 to load media of Executive-R size in the
			 MP tray or envelope tray."
	::= 41023

	periphFPLManualFeedExecutiveRPaper TRAP-TYPE
		ENTERPRISE	netPrinter
		DESCRIPTION
			"The peripheral is waiting for the operator 
			 to load media of Executive-R size in the
			 manual feed tray."
	::= 41123

	periphFPLPCTrayExecutiveRPaper TRAP-TYPE
		ENTERPRISE	netPrinter
		DESCRIPTION
			"The peripheral is waiting for the operator 
			 to load media of Executive-R size in the
			 PC tray or universal tray 2."
	::= 41223

	periphFPLLCTrayExecutiveRPaper TRAP-TYPE
		ENTERPRISE	netPrinter
		DESCRIPTION
			"The peripheral is waiting for the operator 
			 to load media of Executive-R size in the
			 LC tray or universal tray 3."
	::= 41323

	periphFPLEETrayExecutiveRPaper TRAP-TYPE
		ENTERPRISE	netPrinter
		DESCRIPTION
			"The peripheral is waiting for the operator 
			 to load media of Executive-R size in the
			 EE tray or envelope feeder."
	::= 41423

	periphFPLHCITray4ExecutiveRPaper TRAP-TYPE
		ENTERPRISE	netPrinter
		DESCRIPTION
			"The peripheral is waiting for the operator 
			 to load media of Executive-R size in hci tray 4."
	::= 41523

	periphFPLHCITray5ExecutiveRPaper TRAP-TYPE
		ENTERPRISE	netPrinter
		DESCRIPTION
			"The peripheral is waiting for the operator 
			 to load media of Executive-R size in hci tray 5."
	::= 41623

	periphFPLHCITray6ExecutiveRPaper TRAP-TYPE
		ENTERPRISE	netPrinter
		DESCRIPTION
			"The peripheral is waiting for the operator 
			 to load media of Executive-R size in hci tray 6."
	::= 41723

	periphFPLHCITray7ExecutiveRPaper TRAP-TYPE
		ENTERPRISE	netPrinter
		DESCRIPTION
			"The peripheral is waiting for the operator 
			 to load media of Executive-R size in hci tray 7."
	::= 41823

	periphFPLHCITray8OrAllExecutiveRPaper TRAP-TYPE
		ENTERPRISE	netPrinter
		DESCRIPTION
			"The peripheral is waiting for the operator 
			 to load media of Executive-R size in hci tray 8
			 or all input trays are out of media."
	::= 41923

-- A6 Paper

	periphFPLMPTrayA6Paper TRAP-TYPE
		ENTERPRISE	netPrinter
		DESCRIPTION
			"The peripheral is waiting for the operator 
			 to load media of A6 size in the
			 MP tray or envelope tray."
	::= 41024

	periphFPLManualFeedA6Paper TRAP-TYPE
		ENTERPRISE	netPrinter
		DESCRIPTION
			"The peripheral is waiting for the operator 
			 to load media of A6 size in the
			 manual feed tray."
	::= 41124

	periphFPLPCTrayA6Paper TRAP-TYPE
		ENTERPRISE	netPrinter
		DESCRIPTION
			"The peripheral is waiting for the operator 
			 to load media of A6 size in the
			 PC tray or universal tray 2."
	::= 41224

	periphFPLLCTrayA6Paper TRAP-TYPE
		ENTERPRISE	netPrinter
		DESCRIPTION
			"The peripheral is waiting for the operator 
			 to load media of A6 size in the
			 LC tray or universal tray 3."
	::= 41324

	periphFPLEETrayA6Paper TRAP-TYPE
		ENTERPRISE	netPrinter
		DESCRIPTION
			"The peripheral is waiting for the operator 
			 to load media of A6 size in the
			 EE tray or envelope feeder."
	::= 41424

	periphFPLHCITray4A6Paper TRAP-TYPE
		ENTERPRISE	netPrinter
		DESCRIPTION
			"The peripheral is waiting for the operator 
			 to load media of A6 size in hci tray 4."
	::= 41524

	periphFPLHCITray5A6Paper TRAP-TYPE
		ENTERPRISE	netPrinter
		DESCRIPTION
			"The peripheral is waiting for the operator 
			 to load media of A6 size in hci tray 5."
	::= 41624

	periphFPLHCITray6A6Paper TRAP-TYPE
		ENTERPRISE	netPrinter
		DESCRIPTION
			"The peripheral is waiting for the operator 
			 to load media of A6 size in hci tray 6."
	::= 41724

	periphFPLHCITray7A6Paper TRAP-TYPE
		ENTERPRISE	netPrinter
		DESCRIPTION
			"The peripheral is waiting for the operator 
			 to load media of A6 size in hci tray 7."
	::= 41824

	periphFPLHCITray8OrAllA6Paper TRAP-TYPE
		ENTERPRISE	netPrinter
		DESCRIPTION
			"The peripheral is waiting for the operator 
			 to load media of A6 size in hci tray 8
			 or all input trays are out of media."
	::= 41924

-- Foolscap Paper

	periphFPLMPTrayFoolscapPaper TRAP-TYPE
		ENTERPRISE	netPrinter
		DESCRIPTION
			"The peripheral is waiting for the operator 
			 to load media of Foolscap size in the
			 MP tray or envelope tray."
	::= 41025

	periphFPLManualFeedFoolscapPaper TRAP-TYPE
		ENTERPRISE	netPrinter
		DESCRIPTION
			"The peripheral is waiting for the operator 
			 to load media of Foolscap size in the
			 manual feed tray."
	::= 41125

	periphFPLPCTrayFoolscapPaper TRAP-TYPE
		ENTERPRISE	netPrinter
		DESCRIPTION
			"The peripheral is waiting for the operator 
			 to load media of Foolscap size in the
			 PC tray or universal tray 2."
	::= 41225

	periphFPLLCTrayFoolscapPaper TRAP-TYPE
		ENTERPRISE	netPrinter
		DESCRIPTION
			"The peripheral is waiting for the operator 
			 to load media of Foolscap size in the
			 LC tray or universal tray 3."
	::= 41325

	periphFPLEETrayFoolscapPaper TRAP-TYPE
		ENTERPRISE	netPrinter
		DESCRIPTION
			"The peripheral is waiting for the operator 
			 to load media of Foolscap size in the
			 EE tray or envelope feeder."
	::= 41425

	periphFPLHCITray4FoolscapPaper TRAP-TYPE
		ENTERPRISE	netPrinter
		DESCRIPTION
			"The peripheral is waiting for the operator 
			 to load media of Foolscap size in hci tray 4."
	::= 41525

	periphFPLHCITray5FoolscapPaper TRAP-TYPE
		ENTERPRISE	netPrinter
		DESCRIPTION
			"The peripheral is waiting for the operator 
			 to load media of Foolscap size in hci tray 5."
	::= 41625

	periphFPLHCITray6FoolscapPaper TRAP-TYPE
		ENTERPRISE	netPrinter
		DESCRIPTION
			"The peripheral is waiting for the operator 
			 to load media of Foolscap size in hci tray 6."
	::= 41725

	periphFPLHCITray7FoolscapPaper TRAP-TYPE
		ENTERPRISE	netPrinter
		DESCRIPTION
			"The peripheral is waiting for the operator 
			 to load media of Foolscap size in hci tray 7."
	::= 41825

	periphFPLHCITray8OrAllFoolscapPaper TRAP-TYPE
		ENTERPRISE	netPrinter
		DESCRIPTION
			"The peripheral is waiting for the operator 
			 to load media of Foolscap size in hci tray 8
			 or all input trays are out of media."
	::= 41925

-- B6 Paper

	periphFPLMPTrayB6Paper TRAP-TYPE
		ENTERPRISE	netPrinter
		DESCRIPTION
			"The peripheral is waiting for the operator 
			 to load media of B6 size in the
			 MP tray or envelope tray."
	::= 41026

	periphFPLManualFeedB6Paper TRAP-TYPE
		ENTERPRISE	netPrinter
		DESCRIPTION
			"The peripheral is waiting for the operator 
			 to load media of B6 size in the
			 manual feed tray."
	::= 41126

	periphFPLPCTrayB6Paper TRAP-TYPE
		ENTERPRISE	netPrinter
		DESCRIPTION
			"The peripheral is waiting for the operator 
			 to load media of B6 size in the
			 PC tray or universal tray 2."
	::= 41226

	periphFPLLCTrayB6Paper TRAP-TYPE
		ENTERPRISE	netPrinter
		DESCRIPTION
			"The peripheral is waiting for the operator 
			 to load media of B6 size in the
			 LC tray or universal tray 3."
	::= 41326

	periphFPLEETrayB6Paper TRAP-TYPE
		ENTERPRISE	netPrinter
		DESCRIPTION
			"The peripheral is waiting for the operator 
			 to load media of B6 size in the
			 EE tray or envelope feeder."
	::= 41426

	periphFPLHCITray4B6Paper TRAP-TYPE
		ENTERPRISE	netPrinter
		DESCRIPTION
			"The peripheral is waiting for the operator 
			 to load media of B6 size in hci tray 4."
	::= 41526

	periphFPLHCITray5B6Paper TRAP-TYPE
		ENTERPRISE	netPrinter
		DESCRIPTION
			"The peripheral is waiting for the operator 
			 to load media of B6 size in hci tray 5."
	::= 41626

	periphFPLHCITray6B6Paper TRAP-TYPE
		ENTERPRISE	netPrinter
		DESCRIPTION
			"The peripheral is waiting for the operator 
			 to load media of B6 size in hci tray 6."
	::= 41726

	periphFPLHCITray7B6Paper TRAP-TYPE
		ENTERPRISE	netPrinter
		DESCRIPTION
			"The peripheral is waiting for the operator 
			 to load media of B6 size in hci tray 7."
	::= 41826

	periphFPLHCITray8OrAllB6Paper TRAP-TYPE
		ENTERPRISE	netPrinter
		DESCRIPTION
			"The peripheral is waiting for the operator 
			 to load media of B6 size in hci tray 8
			 or all input trays are out of media."
	::= 41926


-- Paper Jam Messages

	periphPaperJamMessage01 TRAP-TYPE
		ENTERPRISE	netPrinter
		DESCRIPTION
			"The peripheral has detected a paper jam."
	::= 42000

	periphPaperJamMessage02 TRAP-TYPE
		ENTERPRISE	netPrinter
		DESCRIPTION
			"The peripheral has detected a paper jam
			 in paper feed 1, paper late jam."
	::= 42001

	periphPaperJamMessage03 TRAP-TYPE
		ENTERPRISE	netPrinter
		DESCRIPTION
			"The peripheral has detected a paper jam
			 in paper feed 2, paper late jam."
	::= 42002

	periphPaperJamMessage04 TRAP-TYPE
		ENTERPRISE	netPrinter
		DESCRIPTION
			"The peripheral has detected a paper jam
			 in fuser output, paper late jam."
	::= 42003

	periphPaperJamMessage05 TRAP-TYPE
		ENTERPRISE	netPrinter
		DESCRIPTION
			"The peripheral has detected a paper jam
			 in fuser output, paper stopped jam."
	::= 42004

	periphPaperJamMessage06 TRAP-TYPE
		ENTERPRISE	netPrinter
		DESCRIPTION
			"The peripheral has detected a paper jam
			 in face down output, paper late jam."
	::= 42005

	periphPaperJamMessage07 TRAP-TYPE
		ENTERPRISE	netPrinter
		DESCRIPTION
			"The peripheral has detected a paper jam
			 in face down output, paper stopped jam."
	::= 42006

	periphPaperJamMessage08 TRAP-TYPE
		ENTERPRISE	netPrinter
		DESCRIPTION
			"The peripheral has detected a paper jam
			 in 2 sided turn around, paper late jam."
	::= 42007

	periphPaperJamMessage09 TRAP-TYPE
		ENTERPRISE	netPrinter
		DESCRIPTION
			"The peripheral has detected a paper jam
			 in 2 sided turn around, paper stopped jam."
	::= 42008

	periphPaperJamMessage10 TRAP-TYPE
		ENTERPRISE	netPrinter
		DESCRIPTION
			"The peripheral has detected a paper jam
			 in 2 sided path, paper late jam."
	::= 42009

	periphPaperJamMessage11 TRAP-TYPE
		ENTERPRISE	netPrinter
		DESCRIPTION
			"The peripheral has detected a paper jam
			 in 2 sided path, paper stopped jam."
	::= 42010

	periphPaperJamMessage12 TRAP-TYPE
		ENTERPRISE	netPrinter
		DESCRIPTION
			"The peripheral has detected a paper jam
			 in the external input device."
	::= 42011

	periphPaperJamMessage13 TRAP-TYPE
		ENTERPRISE	netPrinter
		DESCRIPTION
			"The peripheral has detected a paper jam
			 in the external output device."
	::= 42012

	periphPaperJamMessage14 TRAP-TYPE
		ENTERPRISE	netPrinter
		DESCRIPTION
			"The peripheral has detected a fuser 
			 accordion jam."
	::= 42013

	periphPaperJamMessage15 TRAP-TYPE
		ENTERPRISE	netPrinter
		DESCRIPTION
			"The peripheral has detected a fuser 
			 accordion jam."
	::= 42014

	periphPaperJamMessage16 TRAP-TYPE
		ENTERPRISE	netPrinter
		DESCRIPTION
			"The peripheral could not auto eject paper."
	::= 42015


-- Optional (External) Paper Handling Device Messages

-- Paper Handling Controller

	periphOPHDControllerMessage01 TRAP-TYPE
		ENTERPRISE	netPrinter
		DESCRIPTION
			"Unable to communicate with the paper 
			 handling controller."
	::= 43001

	periphOPHDControllerMessage02 TRAP-TYPE
		ENTERPRISE	netPrinter
		DESCRIPTION
			"Out of sequence packet."
	::= 43002

	periphOPHDControllerMessage03 TRAP-TYPE
		ENTERPRISE	netPrinter
		DESCRIPTION
			"Bad Transaction."
	::= 43003

	periphOPHDControllerMessage04 TRAP-TYPE
		ENTERPRISE	netPrinter
		DESCRIPTION
			"Invalid status bits."
	::= 43004

	periphOPHDControllerMessage05 TRAP-TYPE
		ENTERPRISE	netPrinter
		DESCRIPTION
			"Invalid status code."
	::= 43005

	periphOPHDControllerMessage06 TRAP-TYPE
		ENTERPRISE	netPrinter
		DESCRIPTION
			"Invalid device specified."
	::= 43006

	periphOPHDControllerMessage07 TRAP-TYPE
		ENTERPRISE	netPrinter
		DESCRIPTION
			"Invalid tray specified."
	::= 43007

	periphOPHDControllerMessage08 TRAP-TYPE
		ENTERPRISE	netPrinter
		DESCRIPTION
			"Invalid bin specified."
	::= 43008

	periphOPHDControllerMessage09 TRAP-TYPE
		ENTERPRISE	netPrinter
		DESCRIPTION
			"Invalid number of special purpose bytes."
	::= 43009

	periphOPHDControllerMessage10 TRAP-TYPE
		ENTERPRISE	netPrinter
		DESCRIPTION
			"Invalid number of NVEE bytes."
	::= 43010

	periphOPHDControllerMessage11 TRAP-TYPE
		ENTERPRISE	netPrinter
		DESCRIPTION
			"General paper handling controller
			 malfunction."
	::= 43011

	periphOPHDControllerMessage12 TRAP-TYPE
		ENTERPRISE	netPrinter
		DESCRIPTION
			"Bad paper handling controller
			 RAM."
	::= 43012

	periphOPHDControllerMessage13 TRAP-TYPE
		ENTERPRISE	netPrinter
		DESCRIPTION
			"paper handling controller
			 ROM Checksum error."
	::= 43013

	periphOPHDControllerMessage14 TRAP-TYPE
		ENTERPRISE	netPrinter
		DESCRIPTION
			"Faulty paper handling controller
			 FIFO."
	::= 43014

	periphOPHDControllerMessage15 TRAP-TYPE
		ENTERPRISE	netPrinter
		DESCRIPTION
			"paper handling controller
			 cannot communicate with devices."
	::= 43015

	periphOPHDControllerMessage16 TRAP-TYPE
		ENTERPRISE	netPrinter
		DESCRIPTION
			"paper handling controller
			 never ready during initialization."
	::= 43016

	periphOPHDControllerMessage17 TRAP-TYPE
		ENTERPRISE	netPrinter
		DESCRIPTION
			"FIFO empty when expecting data."
	::= 43017

	periphOPHDControllerMessage18 TRAP-TYPE
		ENTERPRISE	netPrinter
		DESCRIPTION
			"FIFO full when trying to send data."
	::= 43018

	periphOPHDControllerMessage19 TRAP-TYPE
		ENTERPRISE	netPrinter
		DESCRIPTION
			"Invalid page acknowledgement. The 
			 peripheral was not expecting a page
			 acknowledgement."
	::= 43019

	periphOPHDControllerMessage20 TRAP-TYPE
		ENTERPRISE	netPrinter
		DESCRIPTION
			"Page acknowledgement timeout."
	::= 43020

	periphOPHDControllerMessage21 TRAP-TYPE
		ENTERPRISE	netPrinter
		DESCRIPTION
			"Inconsistent paper size."
	::= 43021

	periphOPHDControllerMessage22 TRAP-TYPE
		ENTERPRISE	netPrinter
		DESCRIPTION
			"Wrong page acknowledgement."
	::= 43022

	periphOPHDControllerMessage23 TRAP-TYPE
		ENTERPRISE	netPrinter
		DESCRIPTION
			"Device never ready during 
			 initialization."
	::= 43023

	periphOPHDControllerMessage24 TRAP-TYPE
		ENTERPRISE	netPrinter
		DESCRIPTION
			"Negative Acknowledgement of 
			 ready tray."
	::= 43024

-- Paper Handling Device #01

	periphOPHDDevice01Message01 TRAP-TYPE
		ENTERPRISE	netPrinter
		DESCRIPTION
			"Unable to communicate with the paper 
			 handling controller."
	::= 43101

	periphOPHDDevice01Message02 TRAP-TYPE
		ENTERPRISE	netPrinter
		DESCRIPTION
			"Out of sequence packet."
	::= 43102

	periphOPHDDevice01Message03 TRAP-TYPE
		ENTERPRISE	netPrinter
		DESCRIPTION
			"Bad Transaction."
	::= 43103

	periphOPHDDevice01Message04 TRAP-TYPE
		ENTERPRISE	netPrinter
		DESCRIPTION
			"Invalid status bits."
	::= 43104

	periphOPHDDevice01Message05 TRAP-TYPE
		ENTERPRISE	netPrinter
		DESCRIPTION
			"Invalid status code."
	::= 43105

	periphOPHDDevice01Message06 TRAP-TYPE
		ENTERPRISE	netPrinter
		DESCRIPTION
			"Invalid device specified."
	::= 43106

	periphOPHDDevice01Message07 TRAP-TYPE
		ENTERPRISE	netPrinter
		DESCRIPTION
			"Invalid tray specified."
	::= 43107

	periphOPHDDevice01Message08 TRAP-TYPE
		ENTERPRISE	netPrinter
		DESCRIPTION
			"Invalid bin specified."
	::= 43108

	periphOPHDDevice01Message09 TRAP-TYPE
		ENTERPRISE	netPrinter
		DESCRIPTION
			"Invalid number of special purpose bytes."
	::= 43109

	periphOPHDDevice01Message10 TRAP-TYPE
		ENTERPRISE	netPrinter
		DESCRIPTION
			"Invalid number of NVEE bytes."
	::= 43110

	periphOPHDDevice01Message11 TRAP-TYPE
		ENTERPRISE	netPrinter
		DESCRIPTION
			"General paper handling controller
			 malfunction."
	::= 43111

	periphOPHDDevice01Message12 TRAP-TYPE
		ENTERPRISE	netPrinter
		DESCRIPTION
			"Bad paper handling controller
			 RAM."
	::= 43112

	periphOPHDDevice01Message13 TRAP-TYPE
		ENTERPRISE	netPrinter
		DESCRIPTION
			"paper handling controller
			 ROM Checksum error."
	::= 43113

	periphOPHDDevice01Message14 TRAP-TYPE
		ENTERPRISE	netPrinter
		DESCRIPTION
			"Faulty paper handling controller
			 FIFO."
	::= 43114

	periphOPHDDevice01Message15 TRAP-TYPE
		ENTERPRISE	netPrinter
		DESCRIPTION
			"paper handling controller
			 cannot communicate with devices."
	::= 43115

	periphOPHDDevice01Message16 TRAP-TYPE
		ENTERPRISE	netPrinter
		DESCRIPTION
			"paper handling controller
			 never ready during initialization."
	::= 43116

	periphOPHDDevice01Message17 TRAP-TYPE
		ENTERPRISE	netPrinter
		DESCRIPTION
			"FIFO empty when expecting data."
	::= 43117

	periphOPHDDevice01Message18 TRAP-TYPE
		ENTERPRISE	netPrinter
		DESCRIPTION
			"FIFO full when trying to send data."
	::= 43118

	periphOPHDDevice01Message19 TRAP-TYPE
		ENTERPRISE	netPrinter
		DESCRIPTION
			"Invalid page acknowledgement. The 
			 peripheral was not expecting a page
			 acknowledgement."
	::= 43119

	periphOPHDDevice01Message20 TRAP-TYPE
		ENTERPRISE	netPrinter
		DESCRIPTION
			"Page acknowledgement timeout."
	::= 43120

	periphOPHDDevice01Message21 TRAP-TYPE
		ENTERPRISE	netPrinter
		DESCRIPTION
			"Inconsistent paper size."
	::= 43121

	periphOPHDDevice01Message22 TRAP-TYPE
		ENTERPRISE	netPrinter
		DESCRIPTION
			"Wrong page acknowledgement."
	::= 43122

	periphOPHDDevice01Message23 TRAP-TYPE
		ENTERPRISE	netPrinter
		DESCRIPTION
			"Device never ready during 
			 initialization."
	::= 43123

	periphOPHDDevice01Message24 TRAP-TYPE
		ENTERPRISE	netPrinter
		DESCRIPTION
			"Negative Acknowledgement of 
			 ready tray."
	::= 43124

-- Paper Handling Device #02

	periphOPHDDevice02Message01 TRAP-TYPE
		ENTERPRISE	netPrinter
		DESCRIPTION
			"Unable to communicate with the paper 
			 handling controller."
	::= 43201

	periphOPHDDevice02Message02 TRAP-TYPE
		ENTERPRISE	netPrinter
		DESCRIPTION
			"Out of sequence packet."
	::= 43202

	periphOPHDDevice02Message03 TRAP-TYPE
		ENTERPRISE	netPrinter
		DESCRIPTION
			"Bad Transaction."
	::= 43203

	periphOPHDDevice02Message04 TRAP-TYPE
		ENTERPRISE	netPrinter
		DESCRIPTION
			"Invalid status bits."
	::= 43204

	periphOPHDDevice02Message05 TRAP-TYPE
		ENTERPRISE	netPrinter
		DESCRIPTION
			"Invalid status code."
	::= 43205

	periphOPHDDevice02Message06 TRAP-TYPE
		ENTERPRISE	netPrinter
		DESCRIPTION
			"Invalid device specified."
	::= 43206

	periphOPHDDevice02Message07 TRAP-TYPE
		ENTERPRISE	netPrinter
		DESCRIPTION
			"Invalid tray specified."
	::= 43207

	periphOPHDDevice02Message08 TRAP-TYPE
		ENTERPRISE	netPrinter
		DESCRIPTION
			"Invalid bin specified."
	::= 43208

	periphOPHDDevice02Message09 TRAP-TYPE
		ENTERPRISE	netPrinter
		DESCRIPTION
			"Invalid number of special purpose bytes."
	::= 43209

	periphOPHDDevice02Message10 TRAP-TYPE
		ENTERPRISE	netPrinter
		DESCRIPTION
			"Invalid number of NVEE bytes."
	::= 43210

	periphOPHDDevice02Message11 TRAP-TYPE
		ENTERPRISE	netPrinter
		DESCRIPTION
			"General paper handling controller
			 malfunction."
	::= 43211

	periphOPHDDevice02Message12 TRAP-TYPE
		ENTERPRISE	netPrinter
		DESCRIPTION
			"Bad paper handling controller
			 RAM."
	::= 43212

	periphOPHDDevice02Message13 TRAP-TYPE
		ENTERPRISE	netPrinter
		DESCRIPTION
			"paper handling controller
			 ROM Checksum error."
	::= 43213

	periphOPHDDevice02Message14 TRAP-TYPE
		ENTERPRISE	netPrinter
		DESCRIPTION
			"Faulty paper handling controller
			 FIFO."
	::= 43214

	periphOPHDDevice02Message15 TRAP-TYPE
		ENTERPRISE	netPrinter
		DESCRIPTION
			"paper handling controller
			 cannot communicate with devices."
	::= 43215

	periphOPHDDevice02Message16 TRAP-TYPE
		ENTERPRISE	netPrinter
		DESCRIPTION
			"paper handling controller
			 never ready during initialization."
	::= 43216

	periphOPHDDevice02Message17 TRAP-TYPE
		ENTERPRISE	netPrinter
		DESCRIPTION
			"FIFO empty when expecting data."
	::= 43217

	periphOPHDDevice02Message18 TRAP-TYPE
		ENTERPRISE	netPrinter
		DESCRIPTION
			"FIFO full when trying to send data."
	::= 43218

	periphOPHDDevice02Message19 TRAP-TYPE
		ENTERPRISE	netPrinter
		DESCRIPTION
			"Invalid page acknowledgement. The 
			 peripheral was not expecting a page
			 acknowledgement."
	::= 43219

	periphOPHDDevice02Message20 TRAP-TYPE
		ENTERPRISE	netPrinter
		DESCRIPTION
			"Page acknowledgement timeout."
	::= 43220

	periphOPHDDevice02Message21 TRAP-TYPE
		ENTERPRISE	netPrinter
		DESCRIPTION
			"Inconsistent paper size."
	::= 43221

	periphOPHDDevice02Message22 TRAP-TYPE
		ENTERPRISE	netPrinter
		DESCRIPTION
			"Wrong page acknowledgement."
	::= 43222

	periphOPHDDevice02Message23 TRAP-TYPE
		ENTERPRISE	netPrinter
		DESCRIPTION
			"Device never ready during 
			 initialization."
	::= 43223

	periphOPHDDevice02Message24 TRAP-TYPE
		ENTERPRISE	netPrinter
		DESCRIPTION
			"Negative Acknowledgement of 
			 ready tray."
	::= 43224

-- Paper Handling Device #03

	periphOPHDDevice03Message01 TRAP-TYPE
		ENTERPRISE	netPrinter
		DESCRIPTION
			"Unable to communicate with the paper 
			 handling controller."
	::= 43301

	periphOPHDDevice03Message02 TRAP-TYPE
		ENTERPRISE	netPrinter
		DESCRIPTION
			"Out of sequence packet."
	::= 43302

	periphOPHDDevice03Message03 TRAP-TYPE
		ENTERPRISE	netPrinter
		DESCRIPTION
			"Bad Transaction."
	::= 43303

	periphOPHDDevice03Message04 TRAP-TYPE
		ENTERPRISE	netPrinter
		DESCRIPTION
			"Invalid status bits."
	::= 43304

	periphOPHDDevice03Message05 TRAP-TYPE
		ENTERPRISE	netPrinter
		DESCRIPTION
			"Invalid status code."
	::= 43305

	periphOPHDDevice03Message06 TRAP-TYPE
		ENTERPRISE	netPrinter
		DESCRIPTION
			"Invalid device specified."
	::= 43306

	periphOPHDDevice03Message07 TRAP-TYPE
		ENTERPRISE	netPrinter
		DESCRIPTION
			"Invalid tray specified."
	::= 43307

	periphOPHDDevice03Message08 TRAP-TYPE
		ENTERPRISE	netPrinter
		DESCRIPTION
			"Invalid bin specified."
	::= 43308

	periphOPHDDevice03Message09 TRAP-TYPE
		ENTERPRISE	netPrinter
		DESCRIPTION
			"Invalid number of special purpose bytes."
	::= 43309

	periphOPHDDevice03Message10 TRAP-TYPE
		ENTERPRISE	netPrinter
		DESCRIPTION
			"Invalid number of NVEE bytes."
	::= 43310

	periphOPHDDevice03Message11 TRAP-TYPE
		ENTERPRISE	netPrinter
		DESCRIPTION
			"General paper handling controller
			 malfunction."
	::= 43311

	periphOPHDDevice03Message12 TRAP-TYPE
		ENTERPRISE	netPrinter
		DESCRIPTION
			"Bad paper handling controller
			 RAM."
	::= 43312

	periphOPHDDevice03Message13 TRAP-TYPE
		ENTERPRISE	netPrinter
		DESCRIPTION
			"paper handling controller
			 ROM Checksum error."
	::= 43313

	periphOPHDDevice03Message14 TRAP-TYPE
		ENTERPRISE	netPrinter
		DESCRIPTION
			"Faulty paper handling controller
			 FIFO."
	::= 43314

	periphOPHDDevice03Message15 TRAP-TYPE
		ENTERPRISE	netPrinter
		DESCRIPTION
			"paper handling controller
			 cannot communicate with devices."
	::= 43315

	periphOPHDDevice03Message16 TRAP-TYPE
		ENTERPRISE	netPrinter
		DESCRIPTION
			"paper handling controller
			 never ready during initialization."
	::= 43316

	periphOPHDDevice03Message17 TRAP-TYPE
		ENTERPRISE	netPrinter
		DESCRIPTION
			"FIFO empty when expecting data."
	::= 43317

	periphOPHDDevice03Message18 TRAP-TYPE
		ENTERPRISE	netPrinter
		DESCRIPTION
			"FIFO full when trying to send data."
	::= 43318

	periphOPHDDevice03Message19 TRAP-TYPE
		ENTERPRISE	netPrinter
		DESCRIPTION
			"Invalid page acknowledgement. The 
			 peripheral was not expecting a page
			 acknowledgement."
	::= 43319

	periphOPHDDevice03Message20 TRAP-TYPE
		ENTERPRISE	netPrinter
		DESCRIPTION
			"Page acknowledgement timeout."
	::= 43320

	periphOPHDDevice03Message21 TRAP-TYPE
		ENTERPRISE	netPrinter
		DESCRIPTION
			"Inconsistent paper size."
	::= 43321

	periphOPHDDevice03Message22 TRAP-TYPE
		ENTERPRISE	netPrinter
		DESCRIPTION
			"Wrong page acknowledgement."
	::= 43322

	periphOPHDDevice03Message23 TRAP-TYPE
		ENTERPRISE	netPrinter
		DESCRIPTION
			"Device never ready during 
			 initialization."
	::= 43323

	periphOPHDDevice03Message24 TRAP-TYPE
		ENTERPRISE	netPrinter
		DESCRIPTION
			"Negative Acknowledgement of 
			 ready tray."
	::= 43324

-- Paper Handling Device #04

	periphOPHDDevice04Message01 TRAP-TYPE
		ENTERPRISE	netPrinter
		DESCRIPTION
			"Unable to communicate with the paper 
			 handling controller."
	::= 43401

	periphOPHDDevice04Message02 TRAP-TYPE
		ENTERPRISE	netPrinter
		DESCRIPTION
			"Out of sequence packet."
	::= 43402

	periphOPHDDevice04Message03 TRAP-TYPE
		ENTERPRISE	netPrinter
		DESCRIPTION
			"Bad Transaction."
	::= 43403

	periphOPHDDevice04Message04 TRAP-TYPE
		ENTERPRISE	netPrinter
		DESCRIPTION
			"Invalid status bits."
	::= 43404

	periphOPHDDevice04Message05 TRAP-TYPE
		ENTERPRISE	netPrinter
		DESCRIPTION
			"Invalid status code."
	::= 43405

	periphOPHDDevice04Message06 TRAP-TYPE
		ENTERPRISE	netPrinter
		DESCRIPTION
			"Invalid device specified."
	::= 43406

	periphOPHDDevice04Message07 TRAP-TYPE
		ENTERPRISE	netPrinter
		DESCRIPTION
			"Invalid tray specified."
	::= 43407

	periphOPHDDevice04Message08 TRAP-TYPE
		ENTERPRISE	netPrinter
		DESCRIPTION
			"Invalid bin specified."
	::= 43408

	periphOPHDDevice04Message09 TRAP-TYPE
		ENTERPRISE	netPrinter
		DESCRIPTION
			"Invalid number of special purpose bytes."
	::= 43409

	periphOPHDDevice04Message10 TRAP-TYPE
		ENTERPRISE	netPrinter
		DESCRIPTION
			"Invalid number of NVEE bytes."
	::= 43410

	periphOPHDDevice04Message11 TRAP-TYPE
		ENTERPRISE	netPrinter
		DESCRIPTION
			"General paper handling controller
			 malfunction."
	::= 43411

	periphOPHDDevice04Message12 TRAP-TYPE
		ENTERPRISE	netPrinter
		DESCRIPTION
			"Bad paper handling controller
			 RAM."
	::= 43412

	periphOPHDDevice04Message13 TRAP-TYPE
		ENTERPRISE	netPrinter
		DESCRIPTION
			"paper handling controller
			 ROM Checksum error."
	::= 43413

	periphOPHDDevice04Message14 TRAP-TYPE
		ENTERPRISE	netPrinter
		DESCRIPTION
			"Faulty paper handling controller
			 FIFO."
	::= 43414

	periphOPHDDevice04Message15 TRAP-TYPE
		ENTERPRISE	netPrinter
		DESCRIPTION
			"paper handling controller
			 cannot communicate with devices."
	::= 43415

	periphOPHDDevice04Message16 TRAP-TYPE
		ENTERPRISE	netPrinter
		DESCRIPTION
			"paper handling controller
			 never ready during initialization."
	::= 43416

	periphOPHDDevice04Message17 TRAP-TYPE
		ENTERPRISE	netPrinter
		DESCRIPTION
			"FIFO empty when expecting data."
	::= 43417

	periphOPHDDevice04Message18 TRAP-TYPE
		ENTERPRISE	netPrinter
		DESCRIPTION
			"FIFO full when trying to send data."
	::= 43418

	periphOPHDDevice04Message19 TRAP-TYPE
		ENTERPRISE	netPrinter
		DESCRIPTION
			"Invalid page acknowledgement. The 
			 peripheral was not expecting a page
			 acknowledgement."
	::= 43419

	periphOPHDDevice04Message20 TRAP-TYPE
		ENTERPRISE	netPrinter
		DESCRIPTION
			"Page acknowledgement timeout."
	::= 43420

	periphOPHDDevice04Message21 TRAP-TYPE
		ENTERPRISE	netPrinter
		DESCRIPTION
			"Inconsistent paper size."
	::= 43421

	periphOPHDDevice04Message22 TRAP-TYPE
		ENTERPRISE	netPrinter
		DESCRIPTION
			"Wrong page acknowledgement."
	::= 43422

	periphOPHDDevice04Message23 TRAP-TYPE
		ENTERPRISE	netPrinter
		DESCRIPTION
			"Device never ready during 
			 initialization."
	::= 43423

	periphOPHDDevice04Message24 TRAP-TYPE
		ENTERPRISE	netPrinter
		DESCRIPTION
			"Negative Acknowledgement of 
			 ready tray."
	::= 43424

-- Paper Handling Device #05

	periphOPHDDevice05Message01 TRAP-TYPE
		ENTERPRISE	netPrinter
		DESCRIPTION
			"Unable to communicate with the paper 
			 handling controller."
	::= 43501

	periphOPHDDevice05Message02 TRAP-TYPE
		ENTERPRISE	netPrinter
		DESCRIPTION
			"Out of sequence packet."
	::= 43502

	periphOPHDDevice05Message03 TRAP-TYPE
		ENTERPRISE	netPrinter
		DESCRIPTION
			"Bad Transaction."
	::= 43503

	periphOPHDDevice05Message04 TRAP-TYPE
		ENTERPRISE	netPrinter
		DESCRIPTION
			"Invalid status bits."
	::= 43504

	periphOPHDDevice05Message05 TRAP-TYPE
		ENTERPRISE	netPrinter
		DESCRIPTION
			"Invalid status code."
	::= 43505

	periphOPHDDevice05Message06 TRAP-TYPE
		ENTERPRISE	netPrinter
		DESCRIPTION
			"Invalid device specified."
	::= 43506

	periphOPHDDevice05Message07 TRAP-TYPE
		ENTERPRISE	netPrinter
		DESCRIPTION
			"Invalid tray specified."
	::= 43507

	periphOPHDDevice05Message08 TRAP-TYPE
		ENTERPRISE	netPrinter
		DESCRIPTION
			"Invalid bin specified."
	::= 43508

	periphOPHDDevice05Message09 TRAP-TYPE
		ENTERPRISE	netPrinter
		DESCRIPTION
			"Invalid number of special purpose bytes."
	::= 43509

	periphOPHDDevice05Message10 TRAP-TYPE
		ENTERPRISE	netPrinter
		DESCRIPTION
			"Invalid number of NVEE bytes."
	::= 43510

	periphOPHDDevice05Message11 TRAP-TYPE
		ENTERPRISE	netPrinter
		DESCRIPTION
			"General paper handling controller
			 malfunction."
	::= 43511

	periphOPHDDevice05Message12 TRAP-TYPE
		ENTERPRISE	netPrinter
		DESCRIPTION
			"Bad paper handling controller
			 RAM."
	::= 43512

	periphOPHDDevice05Message13 TRAP-TYPE
		ENTERPRISE	netPrinter
		DESCRIPTION
			"paper handling controller
			 ROM Checksum error."
	::= 43513

	periphOPHDDevice05Message14 TRAP-TYPE
		ENTERPRISE	netPrinter
		DESCRIPTION
			"Faulty paper handling controller
			 FIFO."
	::= 43514

	periphOPHDDevice05Message15 TRAP-TYPE
		ENTERPRISE	netPrinter
		DESCRIPTION
			"paper handling controller
			 cannot communicate with devices."
	::= 43515

	periphOPHDDevice05Message16 TRAP-TYPE
		ENTERPRISE	netPrinter
		DESCRIPTION
			"paper handling controller
			 never ready during initialization."
	::= 43516

	periphOPHDDevice05Message17 TRAP-TYPE
		ENTERPRISE	netPrinter
		DESCRIPTION
			"FIFO empty when expecting data."
	::= 43517

	periphOPHDDevice05Message18 TRAP-TYPE
		ENTERPRISE	netPrinter
		DESCRIPTION
			"FIFO full when trying to send data."
	::= 43518

	periphOPHDDevice05Message19 TRAP-TYPE
		ENTERPRISE	netPrinter
		DESCRIPTION
			"Invalid page acknowledgement. The 
			 peripheral was not expecting a page
			 acknowledgement."
	::= 43519

	periphOPHDDevice05Message20 TRAP-TYPE
		ENTERPRISE	netPrinter
		DESCRIPTION
			"Page acknowledgement timeout."
	::= 43520

	periphOPHDDevice05Message21 TRAP-TYPE
		ENTERPRISE	netPrinter
		DESCRIPTION
			"Inconsistent paper size."
	::= 43521

	periphOPHDDevice05Message22 TRAP-TYPE
		ENTERPRISE	netPrinter
		DESCRIPTION
			"Wrong page acknowledgement."
	::= 43522

	periphOPHDDevice05Message23 TRAP-TYPE
		ENTERPRISE	netPrinter
		DESCRIPTION
			"Device never ready during 
			 initialization."
	::= 43523

	periphOPHDDevice05Message24 TRAP-TYPE
		ENTERPRISE	netPrinter
		DESCRIPTION
			"Negative Acknowledgement of 
			 ready tray."
	::= 43524

-- Paper Jam Messages

-- 0 sheets in peripheral

	periphPJM0SheetsUnknownLocation TRAP-TYPE
		ENTERPRISE	netPrinter
		DESCRIPTION
			"Paper Jam in an unknown location
			 with 0 sheets in the peripheral."
	::= 44000

	periphPJM0SheetsInputArea TRAP-TYPE
		ENTERPRISE	netPrinter
		DESCRIPTION
			"Paper Jam in the paper input area
			 with 0 sheets in the peripheral."
	::= 44001

	periphPJM0SheetsOutputArea TRAP-TYPE
		ENTERPRISE	netPrinter
		DESCRIPTION
			"Paper Jam in the paper output area
			 with 0 sheets in the peripheral.
			 May need to open rear door in peripheral"
	::= 44002

	periphPJM0SheetsTopCover TRAP-TYPE
		ENTERPRISE	netPrinter
		DESCRIPTION
			"Paper Jam in the top cover area
			 with 0 sheets in the peripheral.
			 Remove toner cartridge to clear"
	::= 44003

	periphPJM0SheetsDuplexor TRAP-TYPE
		ENTERPRISE	netPrinter
		DESCRIPTION
			"Paper Jam in the duplexor area
			 with 0 sheets in the peripheral."
	::= 44004

	periphPJM0SheetsDuplexorFrontCover TRAP-TYPE
		ENTERPRISE	netPrinter
		DESCRIPTION
			"Paper Jam in the duplexor front cover area
			 with 0 sheets in the peripheral."
	::= 44005

	periphPJM0SheetsFaceDownOutput TRAP-TYPE
		ENTERPRISE	netPrinter
		DESCRIPTION
			"Paper Jam in the face down output area
			 with 0 sheets in the peripheral."
	::= 44006

	periphPJM0SheetsFrontDoor TRAP-TYPE
		ENTERPRISE	netPrinter
		DESCRIPTION
			"Paper Jam in the front door area
			 with 0 sheets in the peripheral."
	::= 44007

	periphPJM0SheetsLeftDoor TRAP-TYPE
		ENTERPRISE	netPrinter
		DESCRIPTION
			"Paper Jam in the left door area
			 with 0 sheets in the peripheral."
	::= 44008

	periphPJM0SheetsRightDoor TRAP-TYPE
		ENTERPRISE	netPrinter
		DESCRIPTION
			"Paper Jam in the right door area
			 with 0 sheets in the peripheral."
	::= 44009


-- 1 sheet in peripheral

	periphPJM1SheetsUnknownLocation TRAP-TYPE
		ENTERPRISE	netPrinter
		DESCRIPTION
			"Paper Jam in an unknown location
			 with 1 Sheet in the peripheral."
	::= 44100

	periphPJM1SheetsInputArea TRAP-TYPE
		ENTERPRISE	netPrinter
		DESCRIPTION
			"Paper Jam in the paper input area
			 with 1 Sheet in the peripheral."
	::= 44101

	periphPJM1SheetsOutputArea TRAP-TYPE
		ENTERPRISE	netPrinter
		DESCRIPTION
			"Paper Jam in the paper output area
			 with 1 Sheet in the peripheral.
			 May need to open rear door in peripheral"
	::= 44102

	periphPJM1SheetsTopCover TRAP-TYPE
		ENTERPRISE	netPrinter
		DESCRIPTION
			"Paper Jam in the top cover area
			 with 1 Sheet in the peripheral.
			 Remove toner cartridge to clear"
	::= 44103

	periphPJM1SheetsDuplexor TRAP-TYPE
		ENTERPRISE	netPrinter
		DESCRIPTION
			"Paper Jam in the duplexor area
			 with 1 Sheet in the peripheral."
	::= 44104

	periphPJM1SheetsDuplexorFrontCover TRAP-TYPE
		ENTERPRISE	netPrinter
		DESCRIPTION
			"Paper Jam in the duplexor front cover area
			 with 1 Sheet in the peripheral."
	::= 44105

	periphPJM1SheetsFaceDownOutput TRAP-TYPE
		ENTERPRISE	netPrinter
		DESCRIPTION
			"Paper Jam in the face down output area
			 with 1 Sheet in the peripheral."
	::= 44106

	periphPJM1SheetsFrontDoor TRAP-TYPE
		ENTERPRISE	netPrinter
		DESCRIPTION
			"Paper Jam in the front door area
			 with 1 Sheet in the peripheral."
	::= 44107

	periphPJM1SheetsLeftDoor TRAP-TYPE
		ENTERPRISE	netPrinter
		DESCRIPTION
			"Paper Jam in the left door area
			 with 1 Sheet in the peripheral."
	::= 44108

	periphPJM1SheetsRightDoor TRAP-TYPE
		ENTERPRISE	netPrinter
		DESCRIPTION
			"Paper Jam in the right door area
			 with 1 Sheet in the peripheral."
	::= 44109

-- 2 sheets in peripheral

	periphPJM2SheetsUnknownLocation TRAP-TYPE
		ENTERPRISE	netPrinter
		DESCRIPTION
			"Paper Jam in an unknown location
			 with 2 sheets in the peripheral."
	::= 44200

	periphPJM2SheetsInputArea TRAP-TYPE
		ENTERPRISE	netPrinter
		DESCRIPTION
			"Paper Jam in the paper input area
			 with 2 sheets in the peripheral."
	::= 44201

	periphPJM2SheetsOutputArea TRAP-TYPE
		ENTERPRISE	netPrinter
		DESCRIPTION
			"Paper Jam in the paper output area
			 with 2 sheets in the peripheral.
			 May need to open rear door in peripheral"
	::= 44202

	periphPJM2SheetsTopCover TRAP-TYPE
		ENTERPRISE	netPrinter
		DESCRIPTION
			"Paper Jam in the top cover area
			 with 2 sheets in the peripheral.
			 Remove toner cartridge to clear"
	::= 44203

	periphPJM2SheetsDuplexor TRAP-TYPE
		ENTERPRISE	netPrinter
		DESCRIPTION
			"Paper Jam in the duplexor area
			 with 2 sheets in the peripheral."
	::= 44204

	periphPJM2SheetsDuplexorFrontCover TRAP-TYPE
		ENTERPRISE	netPrinter
		DESCRIPTION
			"Paper Jam in the duplexor front cover area
			 with 2 sheets in the peripheral."
	::= 44205

	periphPJM2SheetsFaceDownOutput TRAP-TYPE
		ENTERPRISE	netPrinter
		DESCRIPTION
			"Paper Jam in the face down output area
			 with 2 sheets in the peripheral."
	::= 44206

	periphPJM2SheetsFrontDoor TRAP-TYPE
		ENTERPRISE	netPrinter
		DESCRIPTION
			"Paper Jam in the front door area
			 with 2 sheets in the peripheral."
	::= 44207

	periphPJM2SheetsLeftDoor TRAP-TYPE
		ENTERPRISE	netPrinter
		DESCRIPTION
			"Paper Jam in the left door area
			 with 2 sheets in the peripheral."
	::= 44208

	periphPJM2SheetsRightDoor TRAP-TYPE
		ENTERPRISE	netPrinter
		DESCRIPTION
			"Paper Jam in the right door area
			 with 2 sheets in the peripheral."
	::= 44209

-- 3 sheets in peripheral

	periphPJM3SheetsUnknownLocation TRAP-TYPE
		ENTERPRISE	netPrinter
		DESCRIPTION
			"Paper Jam in an unknown location
			 with 3 sheets in the peripheral."
	::= 44300

	periphPJM3SheetsInputArea TRAP-TYPE
		ENTERPRISE	netPrinter
		DESCRIPTION
			"Paper Jam in the paper input area
			 with 3 sheets in the peripheral."
	::= 44301

	periphPJM3SheetsOutputArea TRAP-TYPE
		ENTERPRISE	netPrinter
		DESCRIPTION
			"Paper Jam in the paper output area
			 with 3 sheets in the peripheral.
			 May need to open rear door in peripheral"
	::= 44302

	periphPJM3SheetsTopCover TRAP-TYPE
		ENTERPRISE	netPrinter
		DESCRIPTION
			"Paper Jam in the top cover area
			 with 3 sheets in the peripheral.
			 Remove toner cartridge to clear"
	::= 44303

	periphPJM3SheetsDuplexor TRAP-TYPE
		ENTERPRISE	netPrinter
		DESCRIPTION
			"Paper Jam in the duplexor area
			 with 3 sheets in the peripheral."
	::= 44304

	periphPJM3SheetsDuplexorFrontCover TRAP-TYPE
		ENTERPRISE	netPrinter
		DESCRIPTION
			"Paper Jam in the duplexor front cover area
			 with 3 sheets in the peripheral."
	::= 44305

	periphPJM3SheetsFaceDownOutput TRAP-TYPE
		ENTERPRISE	netPrinter
		DESCRIPTION
			"Paper Jam in the face down output area
			 with 3 sheets in the peripheral."
	::= 44306

	periphPJM3SheetsFrontDoor TRAP-TYPE
		ENTERPRISE	netPrinter
		DESCRIPTION
			"Paper Jam in the front door area
			 with 3 sheets in the peripheral."
	::= 44307

	periphPJM3SheetsLeftDoor TRAP-TYPE
		ENTERPRISE	netPrinter
		DESCRIPTION
			"Paper Jam in the left door area
			 with 3 sheets in the peripheral."
	::= 44308

	periphPJM3SheetsRightDoor TRAP-TYPE
		ENTERPRISE	netPrinter
		DESCRIPTION
			"Paper Jam in the right door area
			 with 3 sheets in the peripheral."
	::= 44309

-- 4 sheets in peripheral

	periphPJM4SheetsUnknownLocation TRAP-TYPE
		ENTERPRISE	netPrinter
		DESCRIPTION
			"Paper Jam in an unknown location
			 with 4 sheets in the peripheral."
	::= 44400

	periphPJM4SheetsInputArea TRAP-TYPE
		ENTERPRISE	netPrinter
		DESCRIPTION
			"Paper Jam in the paper input area
			 with 4 sheets in the peripheral."
	::= 44401

	periphPJM4SheetsOutputArea TRAP-TYPE
		ENTERPRISE	netPrinter
		DESCRIPTION
			"Paper Jam in the paper output area
			 with 4 sheets in the peripheral.
			 May need to open rear door in peripheral"
	::= 44402

	periphPJM4SheetsTopCover TRAP-TYPE
		ENTERPRISE	netPrinter
		DESCRIPTION
			"Paper Jam in the top cover area
			 with 4 sheets in the peripheral.
			 Remove toner cartridge to clear"
	::= 44403

	periphPJM4SheetsDuplexor TRAP-TYPE
		ENTERPRISE	netPrinter
		DESCRIPTION
			"Paper Jam in the duplexor area
			 with 4 sheets in the peripheral."
	::= 44404

	periphPJM4SheetsDuplexorFrontCover TRAP-TYPE
		ENTERPRISE	netPrinter
		DESCRIPTION
			"Paper Jam in the duplexor front cover area
			 with 4 sheets in the peripheral."
	::= 44405

	periphPJM4SheetsFaceDownOutput TRAP-TYPE
		ENTERPRISE	netPrinter
		DESCRIPTION
			"Paper Jam in the face down output area
			 with 4 sheets in the peripheral."
	::= 44406

	periphPJM4SheetsFrontDoor TRAP-TYPE
		ENTERPRISE	netPrinter
		DESCRIPTION
			"Paper Jam in the front door area
			 with 4 sheets in the peripheral."
	::= 44407

	periphPJM4SheetsLeftDoor TRAP-TYPE
		ENTERPRISE	netPrinter
		DESCRIPTION
			"Paper Jam in the left door area
			 with 4 sheets in the peripheral."
	::= 44408

	periphPJM4SheetsRightDoor TRAP-TYPE
		ENTERPRISE	netPrinter
		DESCRIPTION
			"Paper Jam in the right door area
			 with 4 sheets in the peripheral."
	::= 44409

-- 5 sheets in peripheral

	periphPJM5SheetsUnknownLocation TRAP-TYPE
		ENTERPRISE	netPrinter
		DESCRIPTION
			"Paper Jam in an unknown location
			 with 5 sheets in the peripheral."
	::= 44500

	periphPJM5SheetsInputArea TRAP-TYPE
		ENTERPRISE	netPrinter
		DESCRIPTION
			"Paper Jam in the paper input area
			 with 5 sheets in the peripheral."
	::= 44501

	periphPJM5SheetsOutputArea TRAP-TYPE
		ENTERPRISE	netPrinter
		DESCRIPTION
			"Paper Jam in the paper output area
			 with 5 sheets in the peripheral.
			 May need to open rear door in peripheral"
	::= 44502

	periphPJM5SheetsTopCover TRAP-TYPE
		ENTERPRISE	netPrinter
		DESCRIPTION
			"Paper Jam in the top cover area
			 with 5 sheets in the peripheral.
			 Remove toner cartridge to clear"
	::= 44503

	periphPJM5SheetsDuplexor TRAP-TYPE
		ENTERPRISE	netPrinter
		DESCRIPTION
			"Paper Jam in the duplexor area
			 with 5 sheets in the peripheral."
	::= 44504

	periphPJM5SheetsDuplexorFrontCover TRAP-TYPE
		ENTERPRISE	netPrinter
		DESCRIPTION
			"Paper Jam in the duplexor front cover area
			 with 5 sheets in the peripheral."
	::= 44505

	periphPJM5SheetsFaceDownOutput TRAP-TYPE
		ENTERPRISE	netPrinter
		DESCRIPTION
			"Paper Jam in the face down output area
			 with 5 sheets in the peripheral."
	::= 44506

	periphPJM5SheetsFrontDoor TRAP-TYPE
		ENTERPRISE	netPrinter
		DESCRIPTION
			"Paper Jam in the front door area
			 with 5 sheets in the peripheral."
	::= 44507

	periphPJM5SheetsLeftDoor TRAP-TYPE
		ENTERPRISE	netPrinter
		DESCRIPTION
			"Paper Jam in the left door area
			 with 5 sheets in the peripheral."
	::= 44508

	periphPJM5SheetsRightDoor TRAP-TYPE
		ENTERPRISE	netPrinter
		DESCRIPTION
			"Paper Jam in the right door area
			 with 5 sheets in the peripheral."
	::= 44509

-- 6 sheets in peripheral

	periphPJM6SheetsUnknownLocation TRAP-TYPE
		ENTERPRISE	netPrinter
		DESCRIPTION
			"Paper Jam in an unknown location
			 with 6 sheets in the peripheral."
	::= 44600

	periphPJM6SheetsInputArea TRAP-TYPE
		ENTERPRISE	netPrinter
		DESCRIPTION
			"Paper Jam in the paper input area
			 with 6 sheets in the peripheral."
	::= 44601

	periphPJM6SheetsOutputArea TRAP-TYPE
		ENTERPRISE	netPrinter
		DESCRIPTION
			"Paper Jam in the paper output area
			 with 6 sheets in the peripheral.
			 May need to open rear door in peripheral"
	::= 44602

	periphPJM6SheetsTopCover TRAP-TYPE
		ENTERPRISE	netPrinter
		DESCRIPTION
			"Paper Jam in the top cover area
			 with 6 sheets in the peripheral.
			 Remove toner cartridge to clear"
	::= 44603

	periphPJM6SheetsDuplexor TRAP-TYPE
		ENTERPRISE	netPrinter
		DESCRIPTION
			"Paper Jam in the duplexor area
			 with 6 sheets in the peripheral."
	::= 44604

	periphPJM6SheetsDuplexorFrontCover TRAP-TYPE
		ENTERPRISE	netPrinter
		DESCRIPTION
			"Paper Jam in the duplexor front cover area
			 with 6 sheets in the peripheral."
	::= 44605

	periphPJM6SheetsFaceDownOutput TRAP-TYPE
		ENTERPRISE	netPrinter
		DESCRIPTION
			"Paper Jam in the face down output area
			 with 6 sheets in the peripheral."
	::= 44606

	periphPJM6SheetsFrontDoor TRAP-TYPE
		ENTERPRISE	netPrinter
		DESCRIPTION
			"Paper Jam in the front door area
			 with 6 sheets in the peripheral."
	::= 44607

	periphPJM6SheetsLeftDoor TRAP-TYPE
		ENTERPRISE	netPrinter
		DESCRIPTION
			"Paper Jam in the left door area
			 with 6 sheets in the peripheral."
	::= 44608

	periphPJM6SheetsRightDoor TRAP-TYPE
		ENTERPRISE	netPrinter
		DESCRIPTION
			"Paper Jam in the right door area
			 with 6 sheets in the peripheral."
	::= 44609

-- 7 sheets in peripheral

	periphPJM7SheetsUnknownLocation TRAP-TYPE
		ENTERPRISE	netPrinter
		DESCRIPTION
			"Paper Jam in an unknown location
			 with 7 sheets in the peripheral."
	::= 44700

	periphPJM7SheetsInputArea TRAP-TYPE
		ENTERPRISE	netPrinter
		DESCRIPTION
			"Paper Jam in the paper input area
			 with 7 sheets in the peripheral."
	::= 44701

	periphPJM7SheetsOutputArea TRAP-TYPE
		ENTERPRISE	netPrinter
		DESCRIPTION
			"Paper Jam in the paper output area
			 with 7 sheets in the peripheral.
			 May need to open rear door in peripheral"
	::= 44702

	periphPJM7SheetsTopCover TRAP-TYPE
		ENTERPRISE	netPrinter
		DESCRIPTION
			"Paper Jam in the top cover area
			 with 7 sheets in the peripheral.
			 Remove toner cartridge to clear"
	::= 44703

	periphPJM7SheetsDuplexor TRAP-TYPE
		ENTERPRISE	netPrinter
		DESCRIPTION
			"Paper Jam in the duplexor area
			 with 7 sheets in the peripheral."
	::= 44704

	periphPJM7SheetsDuplexorFrontCover TRAP-TYPE
		ENTERPRISE	netPrinter
		DESCRIPTION
			"Paper Jam in the duplexor front cover area
			 with 7 sheets in the peripheral."
	::= 44705

	periphPJM7SheetsFaceDownOutput TRAP-TYPE
		ENTERPRISE	netPrinter
		DESCRIPTION
			"Paper Jam in the face down output area
			 with 7 sheets in the peripheral."
	::= 44706

	periphPJM7SheetsFrontDoor TRAP-TYPE
		ENTERPRISE	netPrinter
		DESCRIPTION
			"Paper Jam in the front door area
			 with 7 sheets in the peripheral."
	::= 44707

	periphPJM7SheetsLeftDoor TRAP-TYPE
		ENTERPRISE	netPrinter
		DESCRIPTION
			"Paper Jam in the left door area
			 with 7 sheets in the peripheral."
	::= 44708

	periphPJM7SheetsRightDoor TRAP-TYPE
		ENTERPRISE	netPrinter
		DESCRIPTION
			"Paper Jam in the right door area
			 with 7 sheets in the peripheral."
	::= 44709

-- 8 sheets in peripheral

	periphPJM8SheetsUnknownLocation TRAP-TYPE
		ENTERPRISE	netPrinter
		DESCRIPTION
			"Paper Jam in an unknown location
			 with 8 sheets in the peripheral."
	::= 44800

	periphPJM8SheetsInputArea TRAP-TYPE
		ENTERPRISE	netPrinter
		DESCRIPTION
			"Paper Jam in the paper input area
			 with 8 sheets in the peripheral."
	::= 44801

	periphPJM8SheetsOutputArea TRAP-TYPE
		ENTERPRISE	netPrinter
		DESCRIPTION
			"Paper Jam in the paper output area
			 with 8 sheets in the peripheral.
			 May need to open rear door in peripheral"
	::= 44802

	periphPJM8SheetsTopCover TRAP-TYPE
		ENTERPRISE	netPrinter
		DESCRIPTION
			"Paper Jam in the top cover area
			 with 8 sheets in the peripheral.
			 Remove toner cartridge to clear"
	::= 44803

	periphPJM8SheetsDuplexor TRAP-TYPE
		ENTERPRISE	netPrinter
		DESCRIPTION
			"Paper Jam in the duplexor area
			 with 8 sheets in the peripheral."
	::= 44804

	periphPJM8SheetsDuplexorFrontCover TRAP-TYPE
		ENTERPRISE	netPrinter
		DESCRIPTION
			"Paper Jam in the duplexor front cover area
			 with 8 sheets in the peripheral."
	::= 44805

	periphPJM8SheetsFaceDownOutput TRAP-TYPE
		ENTERPRISE	netPrinter
		DESCRIPTION
			"Paper Jam in the face down output area
			 with 8 sheets in the peripheral."
	::= 44806

	periphPJM8SheetsFrontDoor TRAP-TYPE
		ENTERPRISE	netPrinter
		DESCRIPTION
			"Paper Jam in the front door area
			 with 8 sheets in the peripheral."
	::= 44807

	periphPJM8SheetsLeftDoor TRAP-TYPE
		ENTERPRISE	netPrinter
		DESCRIPTION
			"Paper Jam in the left door area
			 with 8 sheets in the peripheral."
	::= 44808

	periphPJM8SheetsRightDoor TRAP-TYPE
		ENTERPRISE	netPrinter
		DESCRIPTION
			"Paper Jam in the right door area
			 with 8 sheets in the peripheral."
	::= 44809

-- 9 sheets in peripheral

	periphPJM9SheetsUnknownLocation TRAP-TYPE
		ENTERPRISE	netPrinter
		DESCRIPTION
			"Paper Jam in an unknown location
			 with 9 sheets in the peripheral."
	::= 44900

	periphPJM9SheetsInputArea TRAP-TYPE
		ENTERPRISE	netPrinter
		DESCRIPTION
			"Paper Jam in the paper input area
			 with 9 sheets in the peripheral."
	::= 44901

	periphPJM9SheetsOutputArea TRAP-TYPE
		ENTERPRISE	netPrinter
		DESCRIPTION
			"Paper Jam in the paper output area
			 with 9 sheets in the peripheral.
			 May need to open rear door in peripheral"
	::= 44902

	periphPJM9SheetsTopCover TRAP-TYPE
		ENTERPRISE	netPrinter
		DESCRIPTION
			"Paper Jam in the top cover area
			 with 9 sheets in the peripheral.
			 Remove toner cartridge to clear"
	::= 44903

	periphPJM9SheetsDuplexor TRAP-TYPE
		ENTERPRISE	netPrinter
		DESCRIPTION
			"Paper Jam in the duplexor area
			 with 9 sheets in the peripheral."
	::= 44904

	periphPJM9SheetsDuplexorFrontCover TRAP-TYPE
		ENTERPRISE	netPrinter
		DESCRIPTION
			"Paper Jam in the duplexor front cover area
			 with 9 sheets in the peripheral."
	::= 44905

	periphPJM9SheetsFaceDownOutput TRAP-TYPE
		ENTERPRISE	netPrinter
		DESCRIPTION
			"Paper Jam in the face down output area
			 with 9 sheets in the peripheral."
	::= 44906

	periphPJM9SheetsFrontDoor TRAP-TYPE
		ENTERPRISE	netPrinter
		DESCRIPTION
			"Paper Jam in the front door area
			 with 9 sheets in the peripheral."
	::= 44907

	periphPJM9SheetsLeftDoor TRAP-TYPE
		ENTERPRISE	netPrinter
		DESCRIPTION
			"Paper Jam in the left door area
			 with 9 sheets in the peripheral."
	::= 44908

	periphPJM9SheetsRightDoor TRAP-TYPE
		ENTERPRISE	netPrinter
		DESCRIPTION
			"Paper Jam in the right door area
			 with 9 sheets in the peripheral."
	::= 44909


-- Other Messages

	periphFuserLowTempFailure TRAP-TYPE
                ENTERPRISE      netPrinter
                DESCRIPTION
                        "Fuser Temperature Failure"
	::= 50008

	periphFuserRisingFailure TRAP-TYPE
                ENTERPRISE      netPrinter
                DESCRIPTION
                        "Fuser Temperature Failure"
	::= 50009

	periphFuserHighTempFailure TRAP-TYPE
                ENTERPRISE      netPrinter
                DESCRIPTION
                        "Fuser Temperature Failure"
	::= 50010

	periphFuserDriveError TRAP-TYPE
                ENTERPRISE      netPrinter
                DESCRIPTION
                        "Fuser Drive Error"
	::= 50011

	periphFanMotorFailureMag TRAP-TYPE
                ENTERPRISE      netPrinter
                DESCRIPTION
                        "Fan Motor Failure"
	::= 50016

	periphMainFanFailureBru TRAP-TYPE
                ENTERPRISE      netPrinter
                DESCRIPTION
                        "Main Fan Failure"
	::= 50019

	periphDuplexMotorFailureMag TRAP-TYPE
                ENTERPRISE      netPrinter
                DESCRIPTION
                        "Duplex Motor Failure"
	::= 50027

END
