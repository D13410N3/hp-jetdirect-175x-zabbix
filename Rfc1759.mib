Printer-MIB DEFINITIONS ::= BEGIN


IMPORTS
        TRAP-TYPE
                FROM RFC-1215
        OBJECT-TYPE
                FROM RFC-1212
        TimeTicks, Counter, experimental
                FROM RFC1155-SMI
        hrStorageIndex, hrDeviceIndex
                FROM HOST-RESOURCES-MIB;

-- created from printmib (9411250000Z)

printmib OBJECT IDENTIFIER ::= { mib-2  43 }
prtGeneral OBJECT IDENTIFIER ::= { printmib  5 }

MediaUnit ::=
    INTEGER {
        tenThousandthsOfInches(3),
        micrometers(4)
    }

CapacityUnit ::=
    INTEGER {
        tenThousandthsOfInches(3),
        micrometers(4),
        sheets(8),
        feet(16),
        meters(17)
    }

SubUnitStatus ::=
    INTEGER

PresentOnOff ::=
    INTEGER {
        other(1),
        on(3),
        off(4),
        notPresent(5)
    }

CodedCharSet ::=
    INTEGER {
        other(1)
    }


prtGeneralTable OBJECT-TYPE
    SYNTAX  SEQUENCE OF PrtGeneralEntry
    ACCESS  not-accessible
    STATUS  mandatory
    DESCRIPTION
           "A table of general information per printer.
        Objects in this table are defined in various
        places in the MIB, nearby the groups to
        which they apply.  They are all defined
        here to minimize the number of tables that would
        otherwise need to exist."
    ::= { prtGeneral  1 }

prtGeneralEntry OBJECT-TYPE
    SYNTAX  PrtGeneralEntry
    ACCESS  not-accessible
    STATUS  mandatory
    DESCRIPTION
           "An entry exists in this table for each
        device entry in the hostmib device table who's type
        is `printer'"
    INDEX   { INTEGER }
    ::= { prtGeneralTable  1 }

PrtGeneralEntry ::=
    SEQUENCE {
        prtGeneralConfigChanges
            Counter,

        prtGeneralCurrentLocalization
            INTEGER (-2147483648..2147483647),

        prtGeneralReset
            INTEGER,

        prtGeneralCurrentOperator
            OCTET STRING,

        prtGeneralServicePerson
            OCTET STRING,

        prtInputDefaultIndex
            INTEGER (-2147483648..2147483647),

        prtOutputDefaultIndex
            INTEGER (-2147483648..2147483647),

        prtMarkerDefaultIndex
            INTEGER (-2147483648..2147483647),

        prtMediaPathDefaultIndex
            INTEGER (-2147483648..2147483647),

        prtConsoleLocalization
            INTEGER (-2147483648..2147483647),

        prtConsoleNumberOfDisplayLines
            INTEGER (-2147483648..2147483647),

        prtConsoleNumberOfDisplayChars
            INTEGER (-2147483648..2147483647),

        prtConsoleDisable
            INTEGER
    }

prtGeneralConfigChanges OBJECT-TYPE
    SYNTAX  Counter
    ACCESS  read-only
    STATUS  mandatory
    DESCRIPTION
           "Counts configuration changes that change the capabilities of
        a printer, such as the addition/deletion of input/output bins,
        the addition/deletion of interpreters, or changes in media
        size.  Such changes will often affect the capability of the
        printer to service certain types of print jobs.
        Management applications may cache infrequently changed
        configuration  information about sub-units on the printer.
        This object should be incremented whenever the agent wishes
        such applications to invalidate that cache and re-download
        all of this configuration information, thereby signalling a
        change in the printer's configuration.
        For example, if an input tray that contained paper of
        different dimensions was added, this counter would be
        incremented.
        As an additional example, this counter would not be
        incremented when an input tray is removed or the level of an
        input device changes."
    ::= { prtGeneralEntry  1 }

prtGeneralCurrentLocalization OBJECT-TYPE
    SYNTAX  INTEGER (-2147483648..2147483647)
    ACCESS  read-write
    STATUS  mandatory
    DESCRIPTION
           "The value of the prtLocalizationIndex corresponding to the
        current language, country, and character set to be used for
        localized string values that are identified as being dependent
        on the value of this object.  Note that this object does not
        apply to localized strings in the prtConsole group or any
        object that is not identified as above."
    ::= { prtGeneralEntry  2 }

prtGeneralReset OBJECT-TYPE
    SYNTAX  INTEGER {
    notResetting(3),
    powerCycleReset(4),
    resetToNVRAM(5),
    resetToFactoryDefaults(6)
}
    ACCESS  read-write
    STATUS  mandatory
    DESCRIPTION
           "Setting this value to `powerCycleReset', `resetToNVRAM', or
        `resetToFactoryDefaults' will result in the resetting of the
        printer.  When read, this object will always have the value
        `notResetting(3)', and a SET of the value `notResetting' shall
        have no effect on the printer.  Some of the defined values are
        optional.  However, every implementation must support at least
        the values `notResetting' and resetToNVRAM'."
    ::= { prtGeneralEntry  3 }

prtCover OBJECT IDENTIFIER ::= { printmib  6 }

prtCoverTable OBJECT-TYPE
    SYNTAX  SEQUENCE OF PrtCoverEntry
    ACCESS  not-accessible
    STATUS  mandatory
    DESCRIPTION
           "A table of the covers and interlocks of the printer."
    ::= { prtCover  1 }

prtCoverEntry OBJECT-TYPE
    SYNTAX  PrtCoverEntry
    ACCESS  not-accessible
    STATUS  mandatory
    DESCRIPTION
           "Information about a cover or interlock.
        Entries may exist in the table for each device
        index whose device type is `printer'."
    INDEX   { INTEGER,  prtCoverIndex }
    ::= { prtCoverTable  1 }

PrtCoverEntry ::=
    SEQUENCE {
        prtCoverIndex
            INTEGER (-2147483648..2147483647),

        prtCoverDescription
            OCTET STRING,

        prtCoverStatus
            INTEGER
    }

prtCoverIndex OBJECT-TYPE
    SYNTAX  INTEGER (-2147483648..2147483647)
    ACCESS  read-only
    STATUS  mandatory
    DESCRIPTION
           "A unique value used by the printer to identify this Cover
        sub-unit.  Although these values may change due to a major
        reconfiguration of the device (e.g. the addition of new
        cover sub-units to the printer), values are expected to
        remain stable across successive printer power cycles."
    ::= { prtCoverEntry  1 }

prtCoverDescription OBJECT-TYPE
    SYNTAX  OCTET STRING
    ACCESS  read-only
    STATUS  mandatory
    DESCRIPTION
           "The manufacturer provided cover sub-mechanism  name in the
        localization specified by prtGeneralCurrentLocalization."
    ::= { prtCoverEntry  2 }

prtCoverStatus OBJECT-TYPE
    SYNTAX  INTEGER {
    other(1),
    doorOpen(3),
    doorClosed(4),
    interlockOpen(5),
    interlockClosed(6)
}
    ACCESS  read-only
    STATUS  mandatory
    DESCRIPTION
           "The status of this cover sub-unit."
    ::= { prtCoverEntry  3 }

prtLocalization OBJECT IDENTIFIER ::= { printmib  7 }

prtLocalizationTable OBJECT-TYPE
    SYNTAX  SEQUENCE OF PrtLocalizationEntry
    ACCESS  not-accessible
    STATUS  mandatory
    DESCRIPTION
           "The available localizations in this printer."
    ::= { prtLocalization  1 }

prtLocalizationEntry OBJECT-TYPE
    SYNTAX  PrtLocalizationEntry
    ACCESS  not-accessible
    STATUS  mandatory
    DESCRIPTION
           "A description of a localization.
        Entries may exist in the table for each device
        index who's device type is `printer'."
    INDEX   { INTEGER,  prtLocalizationIndex }
    ::= { prtLocalizationTable  1 }

PrtLocalizationEntry ::=
    SEQUENCE {
        prtLocalizationIndex
            INTEGER (-2147483648..2147483647),

        prtLocalizationLanguage
            OCTET STRING,

        prtLocalizationCountry
            OCTET STRING,

        prtLocalizationCharacterSet
            CodedCharSet
    }

prtLocalizationIndex OBJECT-TYPE
    SYNTAX  INTEGER (-2147483648..2147483647)
    ACCESS  read-only
    STATUS  mandatory
    DESCRIPTION
           "A unique value used by the printer to identify this
        localization entry.  Although these values may change due to a
        major reconfiguration of the device (e.g., the addition of new
        Cover sub-units to the printer), values are expected to remain
        stable across successive printer power cycles."
    ::= { prtLocalizationEntry  1 }

prtLocalizationLanguage OBJECT-TYPE
    SYNTAX  OCTET STRING
    ACCESS  read-only
    STATUS  mandatory
    DESCRIPTION
           "A two character language code from ISO 639.  Examples EN, GB,
        CA, FR, DE."
    ::= { prtLocalizationEntry  2 }

prtLocalizationCountry OBJECT-TYPE
    SYNTAX  OCTET STRING
    ACCESS  read-only
    STATUS  mandatory
    DESCRIPTION
           "A two character country code from ISO 3166, a blank string
        (two space characters) shall indicate that the country is
        not defined.  Examples: US, FR, DE, ..."
    ::= { prtLocalizationEntry  3 }

prtLocalizationCharacterSet OBJECT-TYPE
    SYNTAX  CodedCharSet
    ACCESS  read-only
    STATUS  mandatory
    DESCRIPTION
           "The coded character set used for this localization."
    ::= { prtLocalizationEntry  4 }

prtStorageRefTable OBJECT-TYPE
    SYNTAX  SEQUENCE OF PrtStorageRefEntry
    ACCESS  not-accessible
    STATUS  mandatory
    DESCRIPTION
           ""
    ::= { prtGeneral  2 }

prtStorageRefEntry OBJECT-TYPE
    SYNTAX  PrtStorageRefEntry
    ACCESS  not-accessible
    STATUS  mandatory
    DESCRIPTION
           "This table will have an entry for each entry in
        the host MIB storage table that represents storage associated
        with a printer managed by this agent."
    INDEX   { INTEGER,  prtStorageRefSeqNumber }
    ::= { prtStorageRefTable  1 }

PrtStorageRefEntry ::=
    SEQUENCE {
        prtStorageRefSeqNumber
            INTEGER (-2147483648..2147483647),

        prtStorageRefIndex
            INTEGER (-2147483648..2147483647)
    }

prtStorageRefSeqNumber OBJECT-TYPE
    SYNTAX  INTEGER (-2147483648..2147483647)
    ACCESS  read-only
    STATUS  mandatory
    DESCRIPTION
           "This value will be unique amongst all entries with a common
        value of hrStorageIndex.
        This object allows a storage entry to point to the multiple
        printer devices with which it is associated."
    ::= { prtStorageRefEntry  1 }

prtStorageRefIndex OBJECT-TYPE
    SYNTAX  INTEGER (-2147483648..2147483647)
    ACCESS  read-only
    STATUS  mandatory
    DESCRIPTION
           "The value of the hrDeviceIndex of the printer device that this
        storageEntry is associated with."
    ::= { prtStorageRefEntry  2 }

prtDeviceRefTable OBJECT-TYPE
    SYNTAX  SEQUENCE OF PrtDeviceRefEntry
    ACCESS  not-accessible
    STATUS  mandatory
    DESCRIPTION
           ""
    ::= { prtGeneral  3 }

prtDeviceRefEntry OBJECT-TYPE
    SYNTAX  PrtDeviceRefEntry
    ACCESS  not-accessible
    STATUS  mandatory
    DESCRIPTION
           "This table will have an entry for each entry in
        the host MIB device table that represents a device associated
        with a printer managed by this agent."
    INDEX   { INTEGER,  prtDeviceRefSeqNumber }
    ::= { prtDeviceRefTable  1 }

PrtDeviceRefEntry ::=
    SEQUENCE {
        prtDeviceRefSeqNumber
            INTEGER (-2147483648..2147483647),

        prtDeviceRefIndex
            INTEGER (-2147483648..2147483647)
    }

prtDeviceRefSeqNumber OBJECT-TYPE
    SYNTAX  INTEGER (-2147483648..2147483647)
    ACCESS  read-only
    STATUS  mandatory
    DESCRIPTION
           "This value will be unique amongst all entries with a common
        value of hrDeviceIndex.
        This object allows a device entry to point to the multiple
        printer devices with which it is associated."
    ::= { prtDeviceRefEntry  1 }

prtDeviceRefIndex OBJECT-TYPE
    SYNTAX  INTEGER (-2147483648..2147483647)
    ACCESS  read-only
    STATUS  mandatory
    DESCRIPTION
           "The value of the hrDeviceIndex of the printer device that this
        deviceEntry is associated with."
    ::= { prtDeviceRefEntry  2 }

prtGeneralCurrentOperator OBJECT-TYPE
    SYNTAX  OCTET STRING
    ACCESS  read-write
    STATUS  mandatory
    DESCRIPTION
           "The name of the current human operator responsible for
        operating this printer. It is suggested that this string
        include information that would enable other humans to reach
        the operator, such as a phone number."
    ::= { prtGeneralEntry  4 }

prtGeneralServicePerson OBJECT-TYPE
    SYNTAX  OCTET STRING
    ACCESS  read-write
    STATUS  mandatory
    DESCRIPTION
           "The name of the last human responsible for servicing
        this printer. It is suggested that this string
        include information that would enable other humans to reach
        the service person, such as a phone number."
    ::= { prtGeneralEntry  5 }

prtInput OBJECT IDENTIFIER ::= { printmib  8 }

prtInputDefaultIndex OBJECT-TYPE
    SYNTAX  INTEGER (-2147483648..2147483647)
    ACCESS  read-write
    STATUS  mandatory
    DESCRIPTION
           "The value of prtInputIndex corresponding to the default input
        sub-unit: that is, this object selects the default source of
        input media."
    ::= { prtGeneralEntry  6 }

prtInputTable OBJECT-TYPE
    SYNTAX  SEQUENCE OF PrtInputEntry
    ACCESS  not-accessible
    STATUS  mandatory
    DESCRIPTION
           "A table of the devices capable of providing media for input
        to the printing process."
    ::= { prtInput  2 }

prtInputEntry OBJECT-TYPE
    SYNTAX  PrtInputEntry
    ACCESS  not-accessible
    STATUS  mandatory
    DESCRIPTION
           "Attributes of a device capable of providing media for input
        to the printing process.
        Entries may exist in the table for each device
        index who's device type is `printer'."
    INDEX   { INTEGER,  prtInputIndex }
    ::= { prtInputTable  1 }

PrtInputEntry ::=
    SEQUENCE {
        prtInputIndex
            INTEGER (-2147483648..2147483647),

        prtInputType
            INTEGER,

        prtInputDimUnit
            MediaUnit,

        prtInputMediaDimFeedDirDeclared
            INTEGER (-2147483648..2147483647),

        prtInputMediaDimXFeedDirDeclared
            INTEGER (-2147483648..2147483647),

        prtInputMediaDimFeedDirChosen
            INTEGER (-2147483648..2147483647),

        prtInputMediaDimXFeedDirChosen
            INTEGER (-2147483648..2147483647),

        prtInputCapacityUnit
            CapacityUnit,

        prtInputMaxCapacity
            INTEGER (-2147483648..2147483647),

        prtInputCurrentLevel
            INTEGER (-2147483648..2147483647),

        prtInputStatus
            SubUnitStatus,

        prtInputMediaName
            OCTET STRING,

        prtInputName
            OCTET STRING,

        prtInputVendorName
            OCTET STRING,

        prtInputModel
            OCTET STRING,

        prtInputVersion
            OCTET STRING,

        prtInputSerialNumber
            OCTET STRING,

        prtInputDescription
            OCTET STRING,

        prtInputSecurity
            PresentOnOff,

        prtInputMediaWeight
            INTEGER (-2147483648..2147483647),

        prtInputMediaType
            OCTET STRING,

        prtInputMediaColor
            OCTET STRING,

        prtInputMediaFormParts
            INTEGER (-2147483648..2147483647)
    }

prtInputIndex OBJECT-TYPE
    SYNTAX  INTEGER (-2147483648..2147483647)
    ACCESS  read-only
    STATUS  mandatory
    DESCRIPTION
           "A unique value used by the printer to identify this input
        sub-unit. Although these values may change due to a major
        reconfiguration of the device (e.g. the addition of new
        input sub-units to the printer), values are expected to
        remain stable across successive printer power cycles."
    ::= { prtInputEntry  1 }

prtInputType OBJECT-TYPE
    SYNTAX  INTEGER {
    other(1),
    unknown(2),
    sheetFeedAutoRemovableTray(3),
    sheetFeedAutoNonRemovableTray(4),
    sheetFeedManual(5),
    continuousRoll(6),
    continuousFanFold(7)
}
    ACCESS  read-only
    STATUS  mandatory
    DESCRIPTION
           "The type of technology (discriminated primarily according to
        feeder mechanism type) employed by the input sub-unit.  Note,
        the Optional Input Class provides for a descriptor field to
        further qualify the other choice."
    ::= { prtInputEntry  2 }

prtInputDimUnit OBJECT-TYPE
    SYNTAX  MediaUnit
    ACCESS  read-only
    STATUS  mandatory
    DESCRIPTION
           "The unit of measurement for use calculating and relaying
        dimensional values for this input sub-unit."
    ::= { prtInputEntry  3 }

prtInputMediaDimFeedDirDeclared OBJECT-TYPE
    SYNTAX  INTEGER (-2147483648..2147483647)
    ACCESS  read-write
    STATUS  mandatory
    DESCRIPTION
           "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown."
    ::= { prtInputEntry  4 }

prtInputMediaDimXFeedDirDeclared OBJECT-TYPE
    SYNTAX  INTEGER (-2147483648..2147483647)
    ACCESS  read-write
    STATUS  mandatory
    DESCRIPTION
           "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown."
    ::= { prtInputEntry  5 }

prtInputMediaDimFeedDirChosen OBJECT-TYPE
    SYNTAX  INTEGER (-2147483648..2147483647)
    ACCESS  read-only
    STATUS  mandatory
    DESCRIPTION
           "The printer will act as if media of the chosen dimension (in
        the feed direction) is present in this input source.  Note
        that this value will be used even if the input tray is empty.
        Feed dimension measurements
        are taken parallel relative to the feed direction
        associated with that sub-unit and are in input sub-unit
        dimensional units (DimUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown."
    ::= { prtInputEntry  6 }

prtInputMediaDimXFeedDirChosen OBJECT-TYPE
    SYNTAX  INTEGER (-2147483648..2147483647)
    ACCESS  read-only
    STATUS  mandatory
    DESCRIPTION
           "The printer will act as if media of the chosen dimension (in
        the cross feed direction) is present in this input source.
        Note that this value will be used even if the input tray is
        empty.  The cross feed direction is ninety degrees relative
        to the feed direction associated with this sub-unit. This
        dimension is measured in input sub-unit dimensional units
        (DimUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown."
    ::= { prtInputEntry  7 }

prtInputCapacityUnit OBJECT-TYPE
    SYNTAX  CapacityUnit
    ACCESS  read-only
    STATUS  mandatory
    DESCRIPTION
           "The unit of measurement for use in calculating and relaying
        capacity values for this input sub-unit."
    ::= { prtInputEntry  8 }

prtInputMaxCapacity OBJECT-TYPE
    SYNTAX  INTEGER (-2147483648..2147483647)
    ACCESS  read-write
    STATUS  mandatory
    DESCRIPTION
           "The maximum capacity of the input sub-unit in input
        sub-unit capacity units (CapacityUnit).  There is no
        convention associated with the media itself so this value
        reflects claimed capacity. If this input sub-unit can
        reliably sense this value, the value is sensed by the
        printer and may not be changed by management requests;
        otherwise, the value may be written (by a Remote
        Contol Panel or a Management Application).
        The value (-1) means other and specifically
        indicates that the sub-unit places no restrictions
        on this parameter.  The value (-2) means unknown."
    ::= { prtInputEntry  9 }

prtInputCurrentLevel OBJECT-TYPE
    SYNTAX  INTEGER (-2147483648..2147483647)
    ACCESS  read-write
    STATUS  mandatory
    DESCRIPTION
           "The current capacity of the input sub-unit in input
        sub-unit capacity units (CapacityUnit). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains."
    ::= { prtInputEntry  10 }

prtInputStatus OBJECT-TYPE
    SYNTAX  SubUnitStatus
    ACCESS  read-only
    STATUS  mandatory
    DESCRIPTION
           "The current status of this input sub-unit."
    ::= { prtInputEntry  11 }

prtInputMediaName OBJECT-TYPE
    SYNTAX  OCTET STRING
    ACCESS  read-write
    STATUS  mandatory
    DESCRIPTION
           "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'."
    ::= { prtInputEntry  12 }

prtInputName OBJECT-TYPE
    SYNTAX  OCTET STRING
    ACCESS  read-write
    STATUS  mandatory
    DESCRIPTION
           "The name assigned to this input sub-unit."
    ::= { prtInputEntry  13 }

prtInputVendorName OBJECT-TYPE
    SYNTAX  OCTET STRING
    ACCESS  read-only
    STATUS  mandatory
    DESCRIPTION
           "The vendor name of this input sub-unit."
    ::= { prtInputEntry  14 }

prtInputModel OBJECT-TYPE
    SYNTAX  OCTET STRING
    ACCESS  read-only
    STATUS  mandatory
    DESCRIPTION
           "The model name of this input sub-unit."
    ::= { prtInputEntry  15 }

prtInputVersion OBJECT-TYPE
    SYNTAX  OCTET STRING
    ACCESS  read-only
    STATUS  mandatory
    DESCRIPTION
           "The version of this input sub-unit."
    ::= { prtInputEntry  16 }

prtInputSerialNumber OBJECT-TYPE
    SYNTAX  OCTET STRING
    ACCESS  read-only
    STATUS  mandatory
    DESCRIPTION
           "The serial number assigned to this input sub-unit."
    ::= { prtInputEntry  17 }

prtInputDescription OBJECT-TYPE
    SYNTAX  OCTET STRING
    ACCESS  read-only
    STATUS  mandatory
    DESCRIPTION
           "A free-form text description of this input
        sub-unit in the localization specified by
        prtGeneralCurrentLocalization."
    ::= { prtInputEntry  18 }

prtInputSecurity OBJECT-TYPE
    SYNTAX  PresentOnOff
    ACCESS  read-write
    STATUS  mandatory
    DESCRIPTION
           "Indicates if this input sub-unit has some security
        associated with it."
    ::= { prtInputEntry  19 }

prtInputMediaWeight OBJECT-TYPE
    SYNTAX  INTEGER (-2147483648..2147483647)
    ACCESS  read-write
    STATUS  mandatory
    DESCRIPTION
           "The weight of the medium associated with this input
        sub-unit in grams / per meter squared. The value (-2) means
        unknown."
    ::= { prtInputEntry  20 }

prtInputMediaType OBJECT-TYPE
    SYNTAX  OCTET STRING
    ACCESS  read-write
    STATUS  mandatory
    DESCRIPTION
           "The name of the type of medium associated with this input
        sub-unit. This name need not be processed by the printer; it
        might simply be displayed to an operator. The standardized
        string values from ISO 10175 (DPA) and ISO 10180 (SPDL) are:
        stationery       Separately cut sheets of an opaque material
        transparency     Separately cut sheets of a transparent material
        envelope         Envelopes that can be used for conventional
        mailing purposes
        envelope-plain   Envelopes that are not preprinted and have no
                         windows
        envelope-window  Envelopes that have windows for addressing
                         purposes
        continuous-long  Continuously connected sheets of an opaque
                         material connected along the long edge
        continuous-short Continuously connected sheets of an opaque
                         material connected along the short edge
        tab-stock        Media with tabs
        multi-part-form  Form medium composed of multiple layers not
                         pre-attached to one another; each sheet may be
                         drawn separately from an input source
        labels           Label stock
        multi-layer      Form medium composed of multiple layers which
                         are pre-attached to one another; e.g., for
                         use with impact printers"
    ::= { prtInputEntry  21 }

prtInputMediaColor OBJECT-TYPE
    SYNTAX  OCTET STRING
    ACCESS  read-write
    STATUS  mandatory
    DESCRIPTION
           "The name of the color of the medium associated with
        this input sub-unit using standardized string values
        from ISO 10175 (DPA) and ISO 10180 (SPDL) which are:
        other
        unknown
        white
        pink
        yellow
        buff
        goldenrod
        blue
        green
        transparent
        Implementors may add additional string values. The naming
        conventions in ISO 9070 are recommended in order to avoid
        potential name clashes."
    ::= { prtInputEntry  22 }

prtInputMediaFormParts OBJECT-TYPE
    SYNTAX  INTEGER (-2147483648..2147483647)
    ACCESS  read-write
    STATUS  mandatory
    DESCRIPTION
           "The number of parts associated with the medium
         associated with this input sub-unit if the medium is a
         multi-part form.  The value (-1) means other and
         specifically indicates that the device places no
         restrictions on this parameter.  The value (-2) means
         unknown."
    ::= { prtInputEntry  23 }

prtOutput OBJECT IDENTIFIER ::= { printmib  9 }

prtOutputDefaultIndex OBJECT-TYPE
    SYNTAX  INTEGER (-2147483648..2147483647)
    ACCESS  read-write
    STATUS  mandatory
    DESCRIPTION
           "The  value of prtOutputIndex  corresponding to the default
        output sub-unit; that is, this object selects the default
        output destination."
    ::= { prtGeneralEntry  7 }

prtOutputTable OBJECT-TYPE
    SYNTAX  SEQUENCE OF PrtOutputEntry
    ACCESS  not-accessible
    STATUS  mandatory
    DESCRIPTION
           "A table of the devices capable of receiving media delivered
        from the printing process."
    ::= { prtOutput  2 }

prtOutputEntry OBJECT-TYPE
    SYNTAX  PrtOutputEntry
    ACCESS  not-accessible
    STATUS  mandatory
    DESCRIPTION
           "Attributes of a device capable of receiving media delivered
        from the printing process.
        Entries may exist in the table for each device
        index who's device type is `printer'."
    INDEX   { INTEGER,  prtOutputIndex }
    ::= { prtOutputTable  1 }

PrtOutputEntry ::=
    SEQUENCE {
        prtOutputIndex
            INTEGER (-2147483648..2147483647),

        prtOutputType
            INTEGER,

        prtOutputCapacityUnit
            CapacityUnit,

        prtOutputMaxCapacity
            INTEGER (-2147483648..2147483647),

        prtOutputRemainingCapacity
            INTEGER (-2147483648..2147483647),

        prtOutputStatus
            SubUnitStatus,

        prtOutputName
            OCTET STRING,

        prtOutputVendorName
            OCTET STRING,

        prtOutputModel
            OCTET STRING,

        prtOutputVersion
            OCTET STRING,

        prtOutputSerialNumber
            OCTET STRING,

        prtOutputDescription
            OCTET STRING,

        prtOutputSecurity
            PresentOnOff,

        prtOutputDimUnit
            MediaUnit,

        prtOutputMaxDimFeedDir
            INTEGER (-2147483648..2147483647),

        prtOutputMaxDimXFeedDir
            INTEGER (-2147483648..2147483647),

        prtOutputMinDimFeedDir
            INTEGER (-2147483648..2147483647),

        prtOutputMinDimXFeedDir
            INTEGER (-2147483648..2147483647),

        prtOutputStackingOrder
            INTEGER,

        prtOutputPageDeliveryOrientation
            INTEGER,

        prtOutputBursting
            PresentOnOff,

        prtOutputDecollating
            PresentOnOff,

        prtOutputPageCollated
            PresentOnOff,

        prtOutputOffsetStacking
            PresentOnOff
    }

prtOutputIndex OBJECT-TYPE
    SYNTAX  INTEGER (-2147483648..2147483647)
    ACCESS  read-only
    STATUS  mandatory
    DESCRIPTION
           "A unique value used by this printer to identify this
        output sub-unit. Although these values may change due
        to a major reconfiguration of the sub-unit (e.g.  the
        addition of new output devices to the printer), values
        are expected to remain stable across successive printer
        power cycles."
    ::= { prtOutputEntry  1 }

prtOutputType OBJECT-TYPE
    SYNTAX  INTEGER {
    other(1),
    unknown(2),
    removableBin(3),
    unRemovableBin(4),
    continuousRollDevice(5),
    mailBox(6),
    continuousFanFold(7)
}
    ACCESS  read-only
    STATUS  mandatory
    DESCRIPTION
           "The type of technology supported by this output sub-unit."
    ::= { prtOutputEntry  2 }

prtOutputCapacityUnit OBJECT-TYPE
    SYNTAX  CapacityUnit
    ACCESS  read-only
    STATUS  mandatory
    DESCRIPTION
           "The unit of measurement for use in calculating and relaying
        capacity values for this output sub-unit."
    ::= { prtOutputEntry  3 }

prtOutputMaxCapacity OBJECT-TYPE
    SYNTAX  INTEGER (-2147483648..2147483647)
    ACCESS  read-write
    STATUS  mandatory
    DESCRIPTION
           "The maximum capacity of this output sub-unit in output
        sub-unit capacity units (CapacityUnit). There is no
        convention associated with the media itself so this value
        essentially reflects claimed capacity. If this output
        sub-unit can reliably sense this value, the value is
        sensed by the printer and may not be changed by management
        requests; otherwise, the value may be written
        (by a Remote Contol Panel or a Management Application).
        The value (-1) means other and specifically indicates
        that the sub-unit places no restrictions on this parameter.
        The value (-2) means unknown."
    ::= { prtOutputEntry  4 }

prtOutputRemainingCapacity OBJECT-TYPE
    SYNTAX  INTEGER (-2147483648..2147483647)
    ACCESS  read-write
    STATUS  mandatory
    DESCRIPTION
           "The remaining capacity of the possible output sub-unit
        capacity in output sub-unit capacity units (CapacityUnit)
        of this output sub-unit. If this output sub-unit can
        reliably sense this value, the value is sensed by the
        printer and may not be modified by management requests;
        otherwise, the value may be written (by
        a Remote Contol Panel or a Management
        Application).  The value (-1) means other and
        specifically indicates that the sub-unit places no
        restrictions on this parameter.  The value (-2) means
        unknown.  The value (-3) means that the printer knows that
        there remains capacity for at least one unit."
    ::= { prtOutputEntry  5 }

prtOutputStatus OBJECT-TYPE
    SYNTAX  SubUnitStatus
    ACCESS  read-only
    STATUS  mandatory
    DESCRIPTION
           "The current status of this output sub-unit."
    ::= { prtOutputEntry  6 }

prtOutputName OBJECT-TYPE
    SYNTAX  OCTET STRING
    ACCESS  read-write
    STATUS  mandatory
    DESCRIPTION
           "The name assigned to this output sub-unit."
    ::= { prtOutputEntry  7 }

prtOutputVendorName OBJECT-TYPE
    SYNTAX  OCTET STRING
    ACCESS  read-only
    STATUS  mandatory
    DESCRIPTION
           "The vendor name of this output sub-unit."
    ::= { prtOutputEntry  8 }

prtOutputModel OBJECT-TYPE
    SYNTAX  OCTET STRING
    ACCESS  read-only
    STATUS  mandatory
    DESCRIPTION
           "The name assigned to this output sub-unit."
    ::= { prtOutputEntry  9 }

prtOutputVersion OBJECT-TYPE
    SYNTAX  OCTET STRING
    ACCESS  read-only
    STATUS  mandatory
    DESCRIPTION
           "The version of this output sub-unit."
    ::= { prtOutputEntry  10 }

prtOutputSerialNumber OBJECT-TYPE
    SYNTAX  OCTET STRING
    ACCESS  read-only
    STATUS  mandatory
    DESCRIPTION
           "The serial number assigned to this output sub-unit."
    ::= { prtOutputEntry  11 }

prtOutputDescription OBJECT-TYPE
    SYNTAX  OCTET STRING
    ACCESS  read-only
    STATUS  mandatory
    DESCRIPTION
           "  A free-form text description of this output sub-unit in the
        localization specified by prtGeneralCurrentLocalization."
    ::= { prtOutputEntry  12 }

prtOutputSecurity OBJECT-TYPE
    SYNTAX  PresentOnOff
    ACCESS  read-write
    STATUS  mandatory
    DESCRIPTION
           "Indicates if this output sub-unit has some security associated
        with it and if that security is enabled or not."
    ::= { prtOutputEntry  13 }

prtOutputDimUnit OBJECT-TYPE
    SYNTAX  MediaUnit
    ACCESS  read-only
    STATUS  mandatory
    DESCRIPTION
           "The unit of measurement for use in calculating and relaying
        dimensional values for this output sub-unit."
    ::= { prtOutputEntry  14 }

prtOutputMaxDimFeedDir OBJECT-TYPE
    SYNTAX  INTEGER (-2147483648..2147483647)
    ACCESS  read-write
    STATUS  mandatory
    DESCRIPTION
           "The maximum dimensions supported by this output sub-unit
        for measurements taken parallel relative to the feed
        direction associated with that sub-unit in output
        sub-unit dimensional units (DimUnit). If this output
        sub-unit can reliably sense this value, the value is
        sensed by the printer and may not be changed with
        management protocol operations."
    ::= { prtOutputEntry  15 }

prtOutputMaxDimXFeedDir OBJECT-TYPE
    SYNTAX  INTEGER (-2147483648..2147483647)
    ACCESS  read-write
    STATUS  mandatory
    DESCRIPTION
           "The maximum dimensions supported by this output sub-unit
        for measurements taken ninety degrees relative to the
        feed direction associated with that sub-unit in output
        sub-unit dimensional units (DimUnit). If this output
        sub-unit can reliably sense this value, the value is
        sensed by the printer and may not be changed with
        management protocol operations."
    ::= { prtOutputEntry  16 }

prtOutputMinDimFeedDir OBJECT-TYPE
    SYNTAX  INTEGER (-2147483648..2147483647)
    ACCESS  read-write
    STATUS  mandatory
    DESCRIPTION
           "The minimum dimensions supported by this output sub-unit
        for measurements taken parallel relative to the feed
        direction associated with that sub-unit in output
        sub-unit dimensional units (DimUnit).  If this output
        sub-unit can reliably sense this value, the value is
        sensed by the printer and may not be changed with
        management protocol operations."
    ::= { prtOutputEntry  17 }

prtOutputMinDimXFeedDir OBJECT-TYPE
    SYNTAX  INTEGER (-2147483648..2147483647)
    ACCESS  read-write
    STATUS  mandatory
    DESCRIPTION
           "The minimum dimensions supported by this output sub-unit
        for measurements taken ninety degrees relative to the
        feed direction associated with that sub-unit in output
        sub-unit dimensional units (DimUnit). If this output
        sub-unit can reliably sense this value, the value is
        sensed by the printer and may not be changed with
        management protocol operations."
    ::= { prtOutputEntry  18 }

prtOutputStackingOrder OBJECT-TYPE
    SYNTAX  INTEGER {
    unknown(2),
    firstToLast(3),
    lastToFirst(4)
}
    ACCESS  read-write
    STATUS  mandatory
    DESCRIPTION
           "The current state of the stacking order for the
        associated output sub-unit. `FirstToLast' means
        that as pages are output the front of the next page is
        placed against the back of the previous page.
        `LasttoFirst' means that as pages are output the back
        of the next page is placed against the front of the
        previous page."
    ::= { prtOutputEntry  19 }

prtOutputPageDeliveryOrientation OBJECT-TYPE
    SYNTAX  INTEGER {
    faceUp(3),
    faceDown(4)
}
    ACCESS  read-write
    STATUS  mandatory
    DESCRIPTION
           "The reading surface that will be `up' when pages are
        delivered to the associated output sub-unit. Values are
        Face-Up and Face-Down. (Note: interpretation of these
        values is in general context-dependent based on locale;
        presentation of these values to an end-user should be
        normalized to the expectations of the user)."
    ::= { prtOutputEntry  20 }

prtOutputBursting OBJECT-TYPE
    SYNTAX  PresentOnOff
    ACCESS  read-write
    STATUS  mandatory
    DESCRIPTION
           "This object indicates that the outputing sub-unit
        supports bursting, and if so, whether the feature is enabled.
        Bursting is the process by which continuous media is separated
        into individual sheets, typically by bursting along pre-formed
        perforations."
    ::= { prtOutputEntry  21 }

prtOutputDecollating OBJECT-TYPE
    SYNTAX  PresentOnOff
    ACCESS  read-write
    STATUS  mandatory
    DESCRIPTION
           "This object indicates that the output supports
        supports decollating, and if so, whether the feature
        is enabled. Decollating is the process by which the
        individual parts within a multi-part form are separated
        and sorted into separate stacks for each part."
    ::= { prtOutputEntry  22 }

prtOutputPageCollated OBJECT-TYPE
    SYNTAX  PresentOnOff
    ACCESS  read-write
    STATUS  mandatory
    DESCRIPTION
           "This object indicates that the output sub-unit
        supports page collation, and if so, whether the feature is
        enabled."
    ::= { prtOutputEntry  23 }

prtOutputOffsetStacking OBJECT-TYPE
    SYNTAX  PresentOnOff
    ACCESS  read-write
    STATUS  mandatory
    DESCRIPTION
           "This object indicates that the output supports
        supports offset stacking, and if so, whether the feature is
        enabled."
    ::= { prtOutputEntry  24 }

prtMarker OBJECT IDENTIFIER ::= { printmib  10 }

prtMarkerDefaultIndex OBJECT-TYPE
    SYNTAX  INTEGER (-2147483648..2147483647)
    ACCESS  read-write
    STATUS  mandatory
    DESCRIPTION
           "The value of prtMarkerIndex  corresponding to the
        default markersub-unit; that is, this object selects the
        default marker."
    ::= { prtGeneralEntry  8 }

prtMarkerTable OBJECT-TYPE
    SYNTAX  SEQUENCE OF PrtMarkerEntry
    ACCESS  not-accessible
    STATUS  mandatory
    DESCRIPTION
           ""
    ::= { prtMarker  2 }

prtMarkerEntry OBJECT-TYPE
    SYNTAX  PrtMarkerEntry
    ACCESS  not-accessible
    STATUS  mandatory
    DESCRIPTION
           "Entries may exist in the table for each device
        index who's device type is `printer'."
    INDEX   { INTEGER,  prtMarkerIndex }
    ::= { prtMarkerTable  1 }

PrtMarkerEntry ::=
    SEQUENCE {
        prtMarkerIndex
            INTEGER (-2147483648..2147483647),

        prtMarkerMarkTech
            INTEGER,

        prtMarkerCounterUnit
            INTEGER,

        prtMarkerLifeCount
            Counter,

        prtMarkerPowerOnCount
            Counter,

        prtMarkerProcessColorants
            INTEGER (-2147483648..2147483647),

        prtMarkerSpotColorants
            INTEGER (-2147483648..2147483647),

        prtMarkerAddressabilityUnit
            INTEGER,

        prtMarkerAddressabilityFeedDir
            INTEGER (-2147483648..2147483647),

        prtMarkerAddressabilityXFeedDir
            INTEGER (-2147483648..2147483647),

        prtMarkerNorthMargin
            INTEGER (-2147483648..2147483647),

        prtMarkerSouthMargin
            INTEGER (-2147483648..2147483647),

        prtMarkerWestMargin
            INTEGER (-2147483648..2147483647),

        prtMarkerEastMargin
            INTEGER (-2147483648..2147483647),

        prtMarkerStatus
            SubUnitStatus
    }

prtMarkerIndex OBJECT-TYPE
    SYNTAX  INTEGER (-2147483648..2147483647)
    ACCESS  read-only
    STATUS  mandatory
    DESCRIPTION
           "A unique value used by the printer to identify this marking
        SubUnitStatus.  Although these values may change due to a major
        reconfiguration of the device (e.g. the addition of new marking
        sub-units to the printer), values are expected to remain
        stable across successive printer power cycles."
    ::= { prtMarkerEntry  1 }

prtMarkerMarkTech OBJECT-TYPE
    SYNTAX  INTEGER {
    other(1),
    unknown(2),
    electrophotographicLED(3),
    electrophotographicLaser(4),
    electrophotographicOther(5),
    impactMovingHeadDotMatrix9pin(6),
    impactMovingHeadDotMatrix24pin(7),
    impactMovingHeadDotMatrixOther(8),
    impactMovingHeadFullyFormed(9),
    impactBand(10),
    impactOther(11),
    inkjetAqueous(12),
    inkjetSolid(13),
    inkjetOther(14),
    pen(15),
    thermalTransfer(16),
    thermalSensitive(17),
    thermalDiffusion(18),
    thermalOther(19),
    electroerosion(20),
    electrostatic(21),
    photographicMicrofiche(22),
    photographicImagesetter(23),
    photographicOther(24),
    ionDeposition(25),
    eBeam(26),
    typesetter(27)
}
    ACCESS  read-only
    STATUS  mandatory
    DESCRIPTION
           "The type of marking technology used for this marking sub-unit."
    ::= { prtMarkerEntry  2 }

prtMarkerCounterUnit OBJECT-TYPE
    SYNTAX  INTEGER {
    tenThousandthsOfInches(3),
    micrometers(4),
    characters(5),
    lines(6),
    impressions(7),
    sheets(8),
    dotRow(9),
    hours(11),
    feet(16),
    meters(17)
}
    ACCESS  read-only
    STATUS  mandatory
    DESCRIPTION
           "The unit that will be used by the printer when reporting
        counter values for this marking sub-unit.  The
        time units of measure are provided for a device like a
        strip recorder that does not or cannot track the physical
        dimensions of the media and does not use characters,
        lines or sheets."
    ::= { prtMarkerEntry  3 }

prtMarkerLifeCount OBJECT-TYPE
    SYNTAX  Counter
    ACCESS  read-only
    STATUS  mandatory
    DESCRIPTION
           "The count of the number of units of measure counted during
        the life of printer using units of measure as specified by
        CounterUnit."
    ::= { prtMarkerEntry  4 }

prtMarkerPowerOnCount OBJECT-TYPE
    SYNTAX  Counter
    ACCESS  read-only
    STATUS  mandatory
    DESCRIPTION
           "The count of the number of units of measure counted since the
        equipment was most recently powered on using units of measure as
        specified by CounterUnit."
    ::= { prtMarkerEntry  5 }

prtMarkerProcessColorants OBJECT-TYPE
    SYNTAX  INTEGER (-2147483648..2147483647)
    ACCESS  read-only
    STATUS  mandatory
    DESCRIPTION
           "The number of process colors supported by this marker.  A
        process color of 1 implies monochrome.  The value of this
        object and SpotColorants cannot both be 0.  Must be 0 or
        greater."
    ::= { prtMarkerEntry  6 }

prtMarkerSpotColorants OBJECT-TYPE
    SYNTAX  INTEGER (-2147483648..2147483647)
    ACCESS  read-only
    STATUS  mandatory
    DESCRIPTION
           "The number of spot colors supported by this marker.  The
        value of this object and ProcessColorants cannot
        both be 0.  Must be 0 or greater."
    ::= { prtMarkerEntry  7 }

prtMarkerAddressabilityUnit OBJECT-TYPE
    SYNTAX  INTEGER {
    tenThousandthsOfInches(3),
    micrometers(4)
}
    ACCESS  read-only
    STATUS  mandatory
    DESCRIPTION
           "The unit of measure of distances."
    ::= { prtMarkerEntry  8 }

prtMarkerAddressabilityFeedDir OBJECT-TYPE
    SYNTAX  INTEGER (-2147483648..2147483647)
    ACCESS  read-only
    STATUS  mandatory
    DESCRIPTION
           "The  number of addressable marking positions in the feed
        direction per 10000 units of measure specified by
        AddressabilityUnit.  A value of (-1) implies 'other' or
        'infinite' while a value of (-2) implies 'unknown'."
    ::= { prtMarkerEntry  9 }

prtMarkerAddressabilityXFeedDir OBJECT-TYPE
    SYNTAX  INTEGER (-2147483648..2147483647)
    ACCESS  read-only
    STATUS  mandatory
    DESCRIPTION
           "The number of addressable marking positions in the cross
        feed direction in 10000 units of measure specified by
        AddressabilityUnit.  A value of (-1) implies 'other' or
        'infinite' while a value of (-2) implies 'unknown'."
    ::= { prtMarkerEntry  10 }

prtMarkerNorthMargin OBJECT-TYPE
    SYNTAX  INTEGER (-2147483648..2147483647)
    ACCESS  read-only
    STATUS  mandatory
    DESCRIPTION
           "The margin, in units identified by AddressabilityUnit,
        from the leading edge of the medium as the medium flows
        throught the marking engine with the side to be imaged
        facing the observer. The leading edge is the North edge
        and the other edges are defined by the normal compass
        layout of  directions with the compass facing the
        observer.  Printing within the area bounded by all four
        margins is guaranteed for all interpreters.   The value
        (-2) means unknown."
    ::= { prtMarkerEntry  11 }

prtMarkerSouthMargin OBJECT-TYPE
    SYNTAX  INTEGER (-2147483648..2147483647)
    ACCESS  read-only
    STATUS  mandatory
    DESCRIPTION
           "The margin from the South edge  (see NorthMargin)
        of the medium in units identified by
        AddressabilityUnit.  Printing within the area bounded by
        all four margins  is guaranteed for all interpreters.
        The value (-2) means unknown."
    ::= { prtMarkerEntry  12 }

prtMarkerWestMargin OBJECT-TYPE
    SYNTAX  INTEGER (-2147483648..2147483647)
    ACCESS  read-only
    STATUS  mandatory
    DESCRIPTION
           "The margin from the West edge (see NorthMargin) of the
        medium in units identified by AddressabilityUnit.
        Printing within the area bouned by all four margins is
        guaranteed for all interpreters.   The value (-2) means
        unknown."
    ::= { prtMarkerEntry  13 }

prtMarkerEastMargin OBJECT-TYPE
    SYNTAX  INTEGER (-2147483648..2147483647)
    ACCESS  read-only
    STATUS  mandatory
    DESCRIPTION
           "The margin from the East edge (see NorthMargin) of the
        medium in units identified by AddressabilityUnit.
        Printing within the area bounded by all four margins is
        guaranteed for all interpreters. The value (-2) means
        unknown."
    ::= { prtMarkerEntry  14 }

prtMarkerStatus OBJECT-TYPE
    SYNTAX  SubUnitStatus
    ACCESS  read-only
    STATUS  mandatory
    DESCRIPTION
           "The current status of this marker sub-unit."
    ::= { prtMarkerEntry  15 }

prtMarkerSupplies OBJECT IDENTIFIER ::= { printmib  11 }

prtMarkerSuppliesTable OBJECT-TYPE
    SYNTAX  SEQUENCE OF PrtMarkerSuppliesEntry
    ACCESS  not-accessible
    STATUS  mandatory
    DESCRIPTION
           "A table of the marker supplies available on this printer."
    ::= { prtMarkerSupplies  1 }

prtMarkerSuppliesEntry OBJECT-TYPE
    SYNTAX  PrtMarkerSuppliesEntry
    ACCESS  not-accessible
    STATUS  mandatory
    DESCRIPTION
           "Attributes of a marker supply.
        Entries may exist in the table for each device
        index who's device type is `printer'."
    INDEX   { INTEGER,  prtMarkerSuppliesIndex }
    ::= { prtMarkerSuppliesTable  1 }

PrtMarkerSuppliesEntry ::=
    SEQUENCE {
        prtMarkerSuppliesIndex
            INTEGER (-2147483648..2147483647),

        prtMarkerSuppliesMarkerIndex
            INTEGER (-2147483648..2147483647),

        prtMarkerSuppliesColorantIndex
            INTEGER (-2147483648..2147483647),

        prtMarkerSuppliesClass
            INTEGER,

        prtMarkerSuppliesType
            INTEGER,

        prtMarkerSuppliesDescription
            OCTET STRING,

        prtMarkerSuppliesSupplyUnit
            INTEGER,

        prtMarkerSuppliesMaxCapacity
            INTEGER (-2147483648..2147483647),

        prtMarkerSuppliesLevel
            INTEGER (-2147483648..2147483647)
    }

prtMarkerSuppliesIndex OBJECT-TYPE
    SYNTAX  INTEGER (-2147483648..2147483647)
    ACCESS  read-only
    STATUS  mandatory
    DESCRIPTION
           "A unique value used by the printer to identify this marker
        supply.  Although these values may change due to a major
        reconfiguration of the device (e.g. the addition of new marker
        supplies to the printer), values are expected to remain stable
        across successive printer power cycles."
    ::= { prtMarkerSuppliesEntry  1 }

prtMarkerSuppliesMarkerIndex OBJECT-TYPE
    SYNTAX  INTEGER (-2147483648..2147483647)
    ACCESS  read-only
    STATUS  mandatory
    DESCRIPTION
           "The value of prtMarkerIndex corresponding to the
        marking sub-unit with which this marker supply
        sub-unit is associated."
    ::= { prtMarkerSuppliesEntry  2 }

prtMarkerSuppliesColorantIndex OBJECT-TYPE
    SYNTAX  INTEGER (-2147483648..2147483647)
    ACCESS  read-only
    STATUS  mandatory
    DESCRIPTION
           "The value of prtMarkerColorantIndex
        corresponding to the colorant with which this
        marker supply sub-unit is associated.  This value
        shall be 0 if there is no colorant table."
    ::= { prtMarkerSuppliesEntry  3 }

prtMarkerSuppliesClass OBJECT-TYPE
    SYNTAX  INTEGER {
    other(1),
    supplyThatIsConsumed(3),
    receptacleThatIsFilled(4)
}
    ACCESS  read-only
    STATUS  mandatory
    DESCRIPTION
           "Indicates whether this supply entity represents a supply
        container that is consumed or a receptacle that is filled."
    ::= { prtMarkerSuppliesEntry  4 }

prtMarkerSuppliesType OBJECT-TYPE
    SYNTAX  INTEGER {
    other(1),
    unknown(2),
    toner(3),
    wasteToner(4),
    ink(5),
    inkCartridge(6),
    inkRibbon(7),
    wasteInk(8),
    opc(9),
    developer(10),
    fuserOil(11),
    solidWax(12),
    ribbonWax(13),
    wasteWax(14)
}
    ACCESS  read-only
    STATUS  mandatory
    DESCRIPTION
           "The type of this supply."
    ::= { prtMarkerSuppliesEntry  5 }

prtMarkerSuppliesDescription OBJECT-TYPE
    SYNTAX  OCTET STRING
    ACCESS  read-only
    STATUS  mandatory
    DESCRIPTION
           "The description of this supply container/receptacle in the
        localization specified by prtGeneralCurrentLocalization."
    ::= { prtMarkerSuppliesEntry  6 }

prtMarkerSuppliesSupplyUnit OBJECT-TYPE
    SYNTAX  INTEGER {
    tenThousandthsOfInches(3),
    micrometers(4),
    thousandthsOfOunces(12),
    tenthsOfGrams(13),
    hundrethsOfFluidOunces(14),
    tenthsOfMilliliters(15)
}
    ACCESS  read-only
    STATUS  mandatory
    DESCRIPTION
           "Unit of this marker supply container/receptacle."
    ::= { prtMarkerSuppliesEntry  7 }

prtMarkerSuppliesMaxCapacity OBJECT-TYPE
    SYNTAX  INTEGER (-2147483648..2147483647)
    ACCESS  read-write
    STATUS  mandatory
    DESCRIPTION
           "The maximum capacity of this supply container/receptacle
        expressed in SupplyUnit. If this supply
        container/receptacle can reliably sense this value, the
        value is sensed by the printer and is read-only;
        otherwise, the value may be written (by a Remote Contol
        Panel or a Management Application). The value (-1) means
        other and specifically indicates that the sub-unit places
        no restrictions on this parameter. The value (-2) means
        unknown."
    ::= { prtMarkerSuppliesEntry  8 }

prtMarkerSuppliesLevel OBJECT-TYPE
    SYNTAX  INTEGER (-2147483648..2147483647)
    ACCESS  read-write
    STATUS  mandatory
    DESCRIPTION
           "The current level if this supply is a container; the
        remaining space if this supply is a receptacle. If this
        supply container/receptacle can reliably sense this
        value, the value is sensed by the printer and is
        read-only; otherwise, the value may be written (by a
        Remote Contol Panel or a Management Application). The
        value (-1) means other and specifically indicates that
        the sub-unit places no restrictions on this parameter.
        The value (-2) means unknown.  A value of (-3) means that the
        printer knows that there is some supply/remaining space,
        respectively."
    ::= { prtMarkerSuppliesEntry  9 }

prtMarkerColorant OBJECT IDENTIFIER ::= { printmib  12 }

prtMarkerColorantTable OBJECT-TYPE
    SYNTAX  SEQUENCE OF PrtMarkerColorantEntry
    ACCESS  not-accessible
    STATUS  mandatory
    DESCRIPTION
           "A table of all of the colorants available on the printer."
    ::= { prtMarkerColorant  1 }

prtMarkerColorantEntry OBJECT-TYPE
    SYNTAX  PrtMarkerColorantEntry
    ACCESS  not-accessible
    STATUS  mandatory
    DESCRIPTION
           "Attributes of a colorant available on the printer.
        Entries may exist in the table for each device
        index who's device type is `printer'."
    INDEX   { INTEGER,  prtMarkerColorantIndex }
    ::= { prtMarkerColorantTable  1 }

PrtMarkerColorantEntry ::=
    SEQUENCE {
        prtMarkerColorantIndex
            INTEGER (-2147483648..2147483647),

        prtMarkerColorantMarkerIndex
            INTEGER (-2147483648..2147483647),

        prtMarkerColorantRole
            INTEGER,

        prtMarkerColorantValue
            OCTET STRING,

        prtMarkerColorantTonality
            INTEGER (-2147483648..2147483647)
    }

prtMarkerColorantIndex OBJECT-TYPE
    SYNTAX  INTEGER (-2147483648..2147483647)
    ACCESS  read-only
    STATUS  mandatory
    DESCRIPTION
           "A unique value used by the printer to identify this colorant.
        Although these values may change due to a major
        reconfiguration of the device (e.g. the addition of new
        colorants to the printer), values are expected to remain
        stable across successive printer power cycles."
    ::= { prtMarkerColorantEntry  1 }

prtMarkerColorantMarkerIndex OBJECT-TYPE
    SYNTAX  INTEGER (-2147483648..2147483647)
    ACCESS  read-only
    STATUS  mandatory
    DESCRIPTION
           "The value of prtMarkerIndex corresponding to the
        marker sub-unit with which this colorant entry is
        associated."
    ::= { prtMarkerColorantEntry  2 }

prtMarkerColorantRole OBJECT-TYPE
    SYNTAX  INTEGER {
    other(1),
    process(3),
    spot(4)
}
    ACCESS  read-only
    STATUS  mandatory
    DESCRIPTION
           "The role played by this colorant."
    ::= { prtMarkerColorantEntry  3 }

prtMarkerColorantValue OBJECT-TYPE
    SYNTAX  OCTET STRING
    ACCESS  read-only
    STATUS  mandatory
    DESCRIPTION
           "The name of the color of this The name of the color of this
        colorant using standardized string names from ISO 10175 (DPA)
        and ISO 10180 (SPDL) which are:
          other
          unknown
          white
          red
          green
          blue
          cyan
          magenta
          yellow
          black
        Implementors may add additional string values. The naming
        conventions in ISO 9070 are recommended in order to avoid
        potential name clashes"
    ::= { prtMarkerColorantEntry  4 }

prtMarkerColorantTonality OBJECT-TYPE
    SYNTAX  INTEGER (-2147483648..2147483647)
    ACCESS  read-only
    STATUS  mandatory
    DESCRIPTION
           "The distinct levels of tonality realizable by a marking
        sub-unit when using this colorant.  This value does not
        include the number of levels of tonal difference that an
        interpreter can obtain by techniques such as half toning.
        This value must be at least 2."
    ::= { prtMarkerColorantEntry  5 }

prtMediaPath OBJECT IDENTIFIER ::= { printmib  13 }

prtMediaPathDefaultIndex OBJECT-TYPE
    SYNTAX  INTEGER (-2147483648..2147483647)
    ACCESS  read-write
    STATUS  mandatory
    DESCRIPTION
           "The value of prtMediaPathIndex corresponding to
        the default media path; that is, the selection of the
        default media path."
    ::= { prtGeneralEntry  9 }

prtMediaPathTable OBJECT-TYPE
    SYNTAX  SEQUENCE OF PrtMediaPathEntry
    ACCESS  not-accessible
    STATUS  mandatory
    DESCRIPTION
           ""
    ::= { prtMediaPath  4 }

prtMediaPathEntry OBJECT-TYPE
    SYNTAX  PrtMediaPathEntry
    ACCESS  not-accessible
    STATUS  mandatory
    DESCRIPTION
           "Entries may exist in the table for each device
        index who's device type is `printer'."
    INDEX   { INTEGER,  prtMediaPathIndex }
    ::= { prtMediaPathTable  1 }

PrtMediaPathEntry ::=
    SEQUENCE {
        prtMediaPathIndex
            INTEGER (-2147483648..2147483647),

        prtMediaPathMaxSpeedPrintUnit
            INTEGER,

        prtMediaPathMediaSizeUnit
            MediaUnit,

        prtMediaPathMaxSpeed
            INTEGER (-2147483648..2147483647),

        prtMediaPathMaxMediaFeedDir
            INTEGER (-2147483648..2147483647),

        prtMediaPathMaxMediaXFeedDir
            INTEGER (-2147483648..2147483647),

        prtMediaPathMinMediaFeedDir
            INTEGER (-2147483648..2147483647),

        prtMediaPathMinMediaXFeedDir
            INTEGER (-2147483648..2147483647),

        prtMediaPathType
            INTEGER,

        prtMediaPathDescription
            OCTET STRING,

        prtMediaPathStatus
            SubUnitStatus
    }

prtMediaPathIndex OBJECT-TYPE
    SYNTAX  INTEGER (-2147483648..2147483647)
    ACCESS  read-only
    STATUS  mandatory
    DESCRIPTION
           "A unique value used by the printer to identify this media
        path. Although these values may change due to a major
        reconfiguration of the device (e.g. the addition of new
        media paths to the printer), values are expected to remain
        stable across successive printer power
        cycles."
    ::= { prtMediaPathEntry  1 }

prtMediaPathMaxSpeedPrintUnit OBJECT-TYPE
    SYNTAX  INTEGER {
    tenThousandthsOfInchesPerHour(3),
    micrometersPerHour(4),
    charactersPerHour(5),
    linesPerHour(6),
    impressionsPerHour(7),
    sheetsPerHour(8),
    dotRowPerHour(9),
    feetPerHour(16),
    metersPerHour(17)
}
    ACCESS  read-only
    STATUS  mandatory
    DESCRIPTION
           "The unit of measure used in specifying the speed of all media
        paths in the printer."
    ::= { prtMediaPathEntry  2 }

prtMediaPathMediaSizeUnit OBJECT-TYPE
    SYNTAX  MediaUnit
    ACCESS  read-only
    STATUS  mandatory
    DESCRIPTION
           "The units of measure of media size for use in calculating and
        relaying dimensional values for all media paths in the printer."
    ::= { prtMediaPathEntry  3 }

prtMediaPathMaxSpeed OBJECT-TYPE
    SYNTAX  INTEGER (-2147483648..2147483647)
    ACCESS  read-only
    STATUS  mandatory
    DESCRIPTION
           "The maximum printing speed of this media path expressed in
        prtMediaPathMaxSpeedUnit's.  A value of (-1) implies
        'other'."
    ::= { prtMediaPathEntry  4 }

prtMediaPathMaxMediaFeedDir OBJECT-TYPE
    SYNTAX  INTEGER (-2147483648..2147483647)
    ACCESS  read-only
    STATUS  mandatory
    DESCRIPTION
           "The maximum physical media size in the feed direction of this
        media path expressed in units of measure specified by
        MediaSizeUnit.  A value of (-1) implies 'unlimited'.  A value
        of (-2) implies 'unknown'"
    ::= { prtMediaPathEntry  5 }

prtMediaPathMaxMediaXFeedDir OBJECT-TYPE
    SYNTAX  INTEGER (-2147483648..2147483647)
    ACCESS  read-only
    STATUS  mandatory
    DESCRIPTION
           "The maximum physical media size across the feed direction of
        this media path expressed in units of measure specified by
        MediaSizeUnit.  A value of (-2) implies 'unknown'."
    ::= { prtMediaPathEntry  6 }

prtMediaPathMinMediaFeedDir OBJECT-TYPE
    SYNTAX  INTEGER (-2147483648..2147483647)
    ACCESS  read-only
    STATUS  mandatory
    DESCRIPTION
           "The minimum physical media size in the feed direction of this
        media path expressed in units of measure specified by
        MediaSizeUnit. A value of (-2) implies 'unknown'."
    ::= { prtMediaPathEntry  7 }

prtMediaPathMinMediaXFeedDir OBJECT-TYPE
    SYNTAX  INTEGER (-2147483648..2147483647)
    ACCESS  read-only
    STATUS  mandatory
    DESCRIPTION
           "The minimum physical media size across the feed direction of
        this media path expressed in units of measure specified by
        MediaSizeUnit.  A value of (-2) implies 'unknown'."
    ::= { prtMediaPathEntry  8 }

prtMediaPathType OBJECT-TYPE
    SYNTAX  INTEGER {
    other(1),
    unknown(2),
    longEdgeBindingDuplex(3),
    shortEdgeBindingDuplex(4),
    simplex(5)
}
    ACCESS  read-only
    STATUS  mandatory
    DESCRIPTION
           "The type of the media path for this media path."
    ::= { prtMediaPathEntry  9 }

prtMediaPathDescription OBJECT-TYPE
    SYNTAX  OCTET STRING
    ACCESS  read-only
    STATUS  mandatory
    DESCRIPTION
           "The manufacturer-provided description of this media path in
        the localization specified by prtGeneralCurrentLocalization."
    ::= { prtMediaPathEntry  10 }

prtMediaPathStatus OBJECT-TYPE
    SYNTAX  SubUnitStatus
    ACCESS  read-only
    STATUS  mandatory
    DESCRIPTION
           "The current status of this media path."
    ::= { prtMediaPathEntry  11 }

prtChannel OBJECT IDENTIFIER ::= { printmib  14 }

prtChannelTable OBJECT-TYPE
    SYNTAX  SEQUENCE OF PrtChannelEntry
    ACCESS  not-accessible
    STATUS  mandatory
    DESCRIPTION
           ""
    ::= { prtChannel  1 }

prtChannelEntry OBJECT-TYPE
    SYNTAX  PrtChannelEntry
    ACCESS  not-accessible
    STATUS  mandatory
    DESCRIPTION
           "Entries may exist in the table for each device
        index who's device type is `printer'."
    INDEX   { INTEGER,  prtChannelIndex }
    ::= { prtChannelTable  1 }

PrtChannelEntry ::=
    SEQUENCE {
        prtChannelIndex
            INTEGER (-2147483648..2147483647),

        prtChannelType
            INTEGER,

        prtChannelProtocolVersion
            OCTET STRING,

        prtChannelCurrentJobCntlLangIndex
            INTEGER (-2147483648..2147483647),

        prtChannelDefaultPageDescLangIndex
            INTEGER (-2147483648..2147483647),

        prtChannelState
            INTEGER,

        prtChannelIfIndex
            INTEGER (-2147483648..2147483647),

        prtChannelStatus
            SubUnitStatus
    }

prtChannelIndex OBJECT-TYPE
    SYNTAX  INTEGER (-2147483648..2147483647)
    ACCESS  read-only
    STATUS  mandatory
    DESCRIPTION
           "A unique value used by the printer to identify this data
        channel.  Although these values may change due to a major
        reconfiguration of the device (e.g. the addition of new data
        channels to the printer), values are expected to remain
        stable across successive printer power cycles."
    ::= { prtChannelEntry  1 }

prtChannelType OBJECT-TYPE
    SYNTAX  INTEGER {
    other(1),
    chSerialPort(3),
    chParallelPort(4),
    chIEEE1284Port(5),
    chSCSIPort(6),
    chAppleTalkPAP(7),
    chLPDServer(8),
    chNetwareRPrinter(9),
    chNetwarePServer(10),
    chPort9100(11),
    chAppSocket(12),
    chFTP(13),
    chTFTP(14),
    chDLCLLCPort(15),
    chIBM3270(16),
    chIBM5250(17),
    chFax(18),
    chIEEE1394(19),
    chTransport1(20),
    chCPAP(21),
    chDCERemoteProcCall(22),
    chONCRemoteProcCall(23),
    chOLE(24),
    chNamedPipe(25),
    chPCPrint(26),
    chServerMessageBlock(27),
    chDPMF(28),
    chDLLAPI(29),
    chVxDAPI(30),
    chSystemObjectManager(31),
    chDECLAT(32),
    chNPAP(33)
}
    ACCESS  read-only
    STATUS  mandatory
    DESCRIPTION
           "The type of this print data channel.  This
        object provides the linkage to ChannelType-specific
        groups that may (conceptually) extend the prtChannelTable
        with additional details about that channel."
    ::= { prtChannelEntry  2 }

prtChannelProtocolVersion OBJECT-TYPE
    SYNTAX  OCTET STRING
    ACCESS  read-only
    STATUS  mandatory
    DESCRIPTION
           "The version of the protocol used on this
        channel.  The format used for version numbering depends
        on prtChannelType."
    ::= { prtChannelEntry  3 }

prtChannelCurrentJobCntlLangIndex OBJECT-TYPE
    SYNTAX  INTEGER (-2147483648..2147483647)
    ACCESS  read-write
    STATUS  mandatory
    DESCRIPTION
           "The value of prtInterpreterIndex  corresponding to the
        Control Language Interpreter for this channel. This
        interpreter defines the syntax used for control
        functions, such as querying or changing environment
        variables and identifying job boundaries (e.g. PJL,
        PostScript, NPAP). Must be 1 or greater."
    ::= { prtChannelEntry  4 }

prtChannelDefaultPageDescLangIndex OBJECT-TYPE
    SYNTAX  INTEGER (-2147483648..2147483647)
    ACCESS  read-write
    STATUS  mandatory
    DESCRIPTION
           "The value of prtInterpreterIndex  corresponding to the
        Page Description Language Interpreter for this channel.
        This interpreter defines the default Page Description
        Language interpreter to be used for the print data unless
        the Control Language is used to select a specific
        interpreter (e.g.,  PCL, PostScript Language,
        auto-sense). Must be 1 or greater."
    ::= { prtChannelEntry  5 }

prtChannelState OBJECT-TYPE
    SYNTAX  INTEGER {
    other(1),
    printDataAccepted(3),
    noDataAccepted(4)
}
    ACCESS  read-write
    STATUS  mandatory
    DESCRIPTION
           "The state of this print data channel.  The value determines
        whether control information and print data is allowed through
        this channel or not."
    ::= { prtChannelEntry  6 }

prtChannelIfIndex OBJECT-TYPE
    SYNTAX  INTEGER (-2147483648..2147483647)
    ACCESS  read-write
    STATUS  mandatory
    DESCRIPTION
           "The value of ifIndex (in the ifTable; see the interface
        section of MIB-2/RFC 1213) which corresponds to this channel.
        When more than one row of the ifTable is relevant, this is
        the index of the row representing the topmost layer in the
        interface hierarchy.  A value of zero indicates that no
        interface is associated with this channel."
    ::= { prtChannelEntry  7 }

prtChannelStatus OBJECT-TYPE
    SYNTAX  SubUnitStatus
    ACCESS  read-only
    STATUS  mandatory
    DESCRIPTION
           "The current status of the channel."
    ::= { prtChannelEntry  8 }

prtInterpreter OBJECT IDENTIFIER ::= { printmib  15 }

prtInterpreterTable OBJECT-TYPE
    SYNTAX  SEQUENCE OF PrtInterpreterEntry
    ACCESS  not-accessible
    STATUS  mandatory
    DESCRIPTION
           ""
    ::= { prtInterpreter  1 }

prtInterpreterEntry OBJECT-TYPE
    SYNTAX  PrtInterpreterEntry
    ACCESS  not-accessible
    STATUS  mandatory
    DESCRIPTION
           "Entries may exist in the table for each device
        index who's device type is `printer'."
    INDEX   { INTEGER,  prtInterpreterIndex }
    ::= { prtInterpreterTable  1 }

PrtInterpreterEntry ::=
    SEQUENCE {
        prtInterpreterIndex
            INTEGER (-2147483648..2147483647),

        prtInterpreterLangFamily
            INTEGER,

        prtInterpreterLangLevel
            OCTET STRING,

        prtInterpreterLangVersion
            OCTET STRING,

        prtInterpreterDescription
            OCTET STRING,

        prtInterpreterVersion
            OCTET STRING,

        prtInterpreterDefaultOrientation
            INTEGER,

        prtInterpreterFeedAddressability
            INTEGER (-2147483648..2147483647),

        prtInterpreterXFeedAddressability
            INTEGER (-2147483648..2147483647),

        prtInterpreterDefaultCharSetIn
            CodedCharSet,

        prtInterpreterDefaultCharSetOut
            CodedCharSet,

        prtInterpreterTwoWay
            INTEGER
    }

prtInterpreterIndex OBJECT-TYPE
    SYNTAX  INTEGER (-2147483648..2147483647)
    ACCESS  read-only
    STATUS  mandatory
    DESCRIPTION
           "A unique value for each PDL or control language for which
        there exists an interpreter or emulator in the printer.  The
        value is used to identify this interpreter. Although these
        values may change due to a major reconfiguration of the device
        (e.g. the addition of new interpreters to the printer), values
        are expected to remain stable across successive printer power
        cycles."
    ::= { prtInterpreterEntry  1 }

prtInterpreterLangFamily OBJECT-TYPE
    SYNTAX  INTEGER {
    other(1),
    langPCL(3),
    langHPGL(4),
    langPJL(5),
    langPS(6),
    langPSPrinter(42),
    langIPDS(7),
    langPPDS(8),
    langEscapeP(9),
    langEpson(10),
    langDDIF(11),
    langInterpress(12),
    langISO6429(13),
    langLineData(14),
    langMODCA(15),
    langREGIS(16),
    langSCS(17),
    langSPDL(18),
    langTEK4014(19),
    langPDS(20),
    langIGP(21),
    langCodeV(22),
    langDSCDSE(23),
    langWPS(24),
    langLN03(25),
    langCCITT(26),
    langQUIC(27),
    langCPAP(28),
    langDecPPL(29),
    langSimpleText(30),
    langNPAP(31),
    langDOC(32),
    langimPress(33),
    langPinwriter(34),
    langNPDL(35),
    langNEC201PL(36),
    langAutomatic(37),
    langPages(38),
    langLIPS(39),
    langTIFF(40),
    langDiagnostic(41),
    langCaPSL(43),
    langEXCL(44),
    langLCDS(45),
    langXES(46)
}
    ACCESS  read-only
    STATUS  mandatory
    DESCRIPTION
           "The family name of a Page Description Language (PDL) or
        control language which this interpreter in the printer can
        interpret or emulate.  This type 2 list of enumerations
        requires review before additional entries are made."
    ::= { prtInterpreterEntry  2 }

prtInterpreterLangLevel OBJECT-TYPE
    SYNTAX  OCTET STRING
    ACCESS  read-only
    STATUS  mandatory
    DESCRIPTION
           "The level of the language which this interpreter is
        interpreting or emulating.  This might contain a value like
        '5e' for an interpreter which is emulating level 5e of the PCL
        language.  It might contain '2' for an interpreter which is
        emulating level 2 of the PostScript language.  Similarly it
        might contain '2' for an interpreter which is emulating level
        2 of the HPGL language."
    ::= { prtInterpreterEntry  3 }

prtInterpreterLangVersion OBJECT-TYPE
    SYNTAX  OCTET STRING
    ACCESS  read-only
    STATUS  mandatory
    DESCRIPTION
           "The date code or version of the language which this interpreter
        is interpreting or emulating."
    ::= { prtInterpreterEntry  4 }

prtInterpreterDescription OBJECT-TYPE
    SYNTAX  OCTET STRING
    ACCESS  read-only
    STATUS  mandatory
    DESCRIPTION
           "A string to identify this interpreter in the localization
        specified by prtGeneralCurrentLocalization as opposed to the
        language which is being interpreted.  It is anticipated that
        this string will allow manufacturers to unambiguously identify
        their interpreters."
    ::= { prtInterpreterEntry  5 }

prtInterpreterVersion OBJECT-TYPE
    SYNTAX  OCTET STRING
    ACCESS  read-only
    STATUS  mandatory
    DESCRIPTION
           "The date code, version number, or other product specific
        information tied to this interpreter.  This value is
        associated with the interpreter, rather than with the version
        of the language which is being interpreted or emulated."
    ::= { prtInterpreterEntry  6 }

prtInterpreterDefaultOrientation OBJECT-TYPE
    SYNTAX  INTEGER {
    other(1),
    portrait(3),
    landscape(4)
}
    ACCESS  read-write
    STATUS  mandatory
    DESCRIPTION
           "The current orientation default for this interpreter.  This
        value may be overridden for a particular job (e.g., by a
        command in the input data stream)."
    ::= { prtInterpreterEntry  7 }

prtInterpreterFeedAddressability OBJECT-TYPE
    SYNTAX  INTEGER (-2147483648..2147483647)
    ACCESS  read-only
    STATUS  mandatory
    DESCRIPTION
           "The maximum interpreter addressability in the feed
        direction in 10000 prtMarkerAddressabilityUnit s (see
        prtMarkerAddressabilityFeedDir ) for this interpreter.
        The value (-1) means other and specifically indicates
        that the sub-unit places no restrictions on this parameter."
    ::= { prtInterpreterEntry  8 }

prtInterpreterXFeedAddressability OBJECT-TYPE
    SYNTAX  INTEGER (-2147483648..2147483647)
    ACCESS  read-only
    STATUS  mandatory
    DESCRIPTION
           "The maximum interpreter addressability in the cross feed
        direction in 10000 prtMarkerAddressabilityUnit s (see
        prtMarkerAddressabilityXFeedDir) for this interpreter.
        The value (-1) means other and specifically indicates
        that the sub-unit places no restrictions on this
        parameter."
    ::= { prtInterpreterEntry  9 }

prtInterpreterDefaultCharSetIn OBJECT-TYPE
    SYNTAX  CodedCharSet
    ACCESS  read-write
    STATUS  mandatory
    DESCRIPTION
           "The default coded character set for input octets
        encountered outside a context in which the Page
        Description Language established the interpretation
        of the octets.
        This value shall be (2) if there is no default."
    ::= { prtInterpreterEntry  10 }

prtInterpreterDefaultCharSetOut OBJECT-TYPE
    SYNTAX  CodedCharSet
    ACCESS  read-write
    STATUS  mandatory
    DESCRIPTION
           "The default character set for data coming from this interpreter
        through the printer's output channel.
        This value shall be (2) if there is no default."
    ::= { prtInterpreterEntry  11 }

prtInterpreterTwoWay OBJECT-TYPE
    SYNTAX  INTEGER {
    yes(3),
    no(4)
}
    ACCESS  read-only
    STATUS  mandatory
    DESCRIPTION
           "Indicates whether or not this interpreter returns information
        back to the host."
    ::= { prtInterpreterEntry  12 }

prtConsoleLocalization OBJECT-TYPE
    SYNTAX  INTEGER (-2147483648..2147483647)
    ACCESS  read-write
    STATUS  mandatory
    DESCRIPTION
           "The value of the prtLocalizationIndex corresponding to
        the language, country, and character set to be used for the
        console.  This localization applies both to the actual display
        on the console as well as the encoding of these console
        objects in management operations."
    ::= { prtGeneralEntry  10 }

prtConsoleNumberOfDisplayLines OBJECT-TYPE
    SYNTAX  INTEGER (-2147483648..2147483647)
    ACCESS  read-only
    STATUS  mandatory
    DESCRIPTION
           "The number of lines on the printer's physical
        display.  This value is 0 if there are no lines on the
        physical display or if there is no physical display"
    ::= { prtGeneralEntry  11 }

prtConsoleNumberOfDisplayChars OBJECT-TYPE
    SYNTAX  INTEGER (-2147483648..2147483647)
    ACCESS  read-only
    STATUS  mandatory
    DESCRIPTION
           "The number of characters per line displayed on the physical
        display.  This value is 0 if there are no lines on the
        physical display or if there is no physical display"
    ::= { prtGeneralEntry  12 }

prtConsoleDisable OBJECT-TYPE
    SYNTAX  INTEGER {
    enabled(3),
    disabled(4)
}
    ACCESS  read-write
    STATUS  mandatory
    DESCRIPTION
           "This object enables or disables manual input from the
        operators console."
    ::= { prtGeneralEntry  13 }

prtConsoleDisplayBuffer OBJECT IDENTIFIER ::= { printmib  16 }

prtConsoleDisplayBufferTable OBJECT-TYPE
    SYNTAX  SEQUENCE OF PrtConsoleDisplayBufferEntry
    ACCESS  not-accessible
    STATUS  mandatory
    DESCRIPTION
           ""
    ::= { prtConsoleDisplayBuffer  5 }

prtConsoleDisplayBufferEntry OBJECT-TYPE
    SYNTAX  PrtConsoleDisplayBufferEntry
    ACCESS  not-accessible
    STATUS  mandatory
    DESCRIPTION
           "This table contains one entry for each physical line on
        the display.  Lines cannot be added or deleted.
        Entries may exist in the table for each device
        index who's device type is `printer'."
    INDEX   { INTEGER,  prtConsoleDisplayBufferIndex }
    ::= { prtConsoleDisplayBufferTable  1 }

PrtConsoleDisplayBufferEntry ::=
    SEQUENCE {
        prtConsoleDisplayBufferIndex
            INTEGER (-2147483648..2147483647),

        prtConsoleDisplayBufferText
            OCTET STRING
    }

prtConsoleDisplayBufferIndex OBJECT-TYPE
    SYNTAX  INTEGER (-2147483648..2147483647)
    ACCESS  read-only
    STATUS  mandatory
    DESCRIPTION
           "A unique value for each console line in the printer.  The
        value is used to identify this console line. Although
        these values may change due to a major reconfiguration of
        the device (e.g. the addition of new console lines to the
        printer), values are expected to remain stable across
        successive printer power cycles."
    ::= { prtConsoleDisplayBufferEntry  1 }

prtConsoleDisplayBufferText OBJECT-TYPE
    SYNTAX  OCTET STRING
    ACCESS  read-write
    STATUS  mandatory
    DESCRIPTION
           "The content of a line in the logical display buffer of
        the operator's console of the printer.  When a write
        operation occurs, normally a critical message, to one of
        the LineText strings, the agent should make that line
        displayable if a physical display is present.  Writing
        a zero length string clears the line.  It is an
        implementation-specific matter as to whether the agent allows
        a line to be overwritten before it has been cleared.
        Printer generated strings shall be in the localization
        specified by ConsoleLocalization.  Management Application
        generated strings should be localized by the Management
        Application."
    ::= { prtConsoleDisplayBufferEntry  2 }

prtConsoleLights OBJECT IDENTIFIER ::= { printmib  17 }

prtConsoleLightTable OBJECT-TYPE
    SYNTAX  SEQUENCE OF PrtConsoleLightEntry
    ACCESS  not-accessible
    STATUS  mandatory
    DESCRIPTION
           ""
    ::= { prtConsoleLights  6 }

prtConsoleLightEntry OBJECT-TYPE
    SYNTAX  PrtConsoleLightEntry
    ACCESS  not-accessible
    STATUS  mandatory
    DESCRIPTION
           "Entries may exist in the table for each device
        index who's device type is `printer'."
    INDEX   { INTEGER,  prtConsoleLightIndex }
    ::= { prtConsoleLightTable  1 }

PrtConsoleLightEntry ::=
    SEQUENCE {
        prtConsoleLightIndex
            INTEGER (-2147483648..2147483647),

        prtConsoleOnTime
            INTEGER (-2147483648..2147483647),

        prtConsoleOffTime
            INTEGER (-2147483648..2147483647),

        prtConsoleColor
            INTEGER,

        prtConsoleDescription
            OCTET STRING
    }

prtConsoleLightIndex OBJECT-TYPE
    SYNTAX  INTEGER (-2147483648..2147483647)
    ACCESS  read-only
    STATUS  mandatory
    DESCRIPTION
           "A unique value used by the printer to identify this light.
        Although these values may change due to a major
        reconfiguration of the device (e.g. the addition of new lights
        to the printer), values are expected to remain stable across
        successive printer power cycles."
    ::= { prtConsoleLightEntry  1 }

prtConsoleOnTime OBJECT-TYPE
    SYNTAX  INTEGER (-2147483648..2147483647)
    ACCESS  read-write
    STATUS  mandatory
    DESCRIPTION
           "The on time in milliseconds of blinking of this light; 0
        indicates off always.  If both prtConsoleOnTime
        and prtConsoleOffTime are 0, then the light is
        always off."
    ::= { prtConsoleLightEntry  2 }

prtConsoleOffTime OBJECT-TYPE
    SYNTAX  INTEGER (-2147483648..2147483647)
    ACCESS  read-write
    STATUS  mandatory
    DESCRIPTION
           "The off time in milliseconds of blinking of this light; 0
        indicates on always.  If both prtConsoleOnTime
        and prtConsoleOffTime are 0, then the light is
        always off."
    ::= { prtConsoleLightEntry  3 }

prtConsoleColor OBJECT-TYPE
    SYNTAX  INTEGER {
    other(1),
    unknown(2),
    white(3),
    red(4),
    green(5),
    blue(6),
    cyan(7),
    magenta(8),
    yellow(9)
}
    ACCESS  read-only
    STATUS  mandatory
    DESCRIPTION
           "The color of this light."
    ::= { prtConsoleLightEntry  4 }

prtConsoleDescription OBJECT-TYPE
    SYNTAX  OCTET STRING
    ACCESS  read-only
    STATUS  mandatory
    DESCRIPTION
           "The vendor description or label of this light in the
        localization specified by prtConsoleLocalization."
    ::= { prtConsoleLightEntry  5 }

prtAlert OBJECT IDENTIFIER ::= { printmib  18 }

prtAlertTable OBJECT-TYPE
    SYNTAX  SEQUENCE OF PrtAlertEntry
    ACCESS  not-accessible
    STATUS  mandatory
    DESCRIPTION
           ""
    ::= { prtAlert  1 }

prtAlertEntry OBJECT-TYPE
    SYNTAX  PrtAlertEntry
    ACCESS  not-accessible
    STATUS  mandatory
    DESCRIPTION
           "Entries may exist in the table for each device
        index who's device type is `printer'."
    INDEX   { INTEGER,  prtAlertIndex }
    ::= { prtAlertTable  1 }

PrtAlertEntry ::=
    SEQUENCE {
        prtAlertIndex
            INTEGER (-2147483648..2147483647),

        prtAlertSeverityLevel
            INTEGER,

        prtAlertTrainingLevel
            INTEGER,

        prtAlertGroup
            INTEGER,

        prtAlertGroupIndex
            INTEGER (-2147483648..2147483647),

        prtAlertLocation
            INTEGER (-2147483648..2147483647),

        prtAlertCode
            INTEGER,

        prtAlertDescription
            OCTET STRING,

        prtAlertTime
            TimeTicks
    }

prtAlertIndex OBJECT-TYPE
    SYNTAX  INTEGER (-2147483648..2147483647)
    ACCESS  read-only
    STATUS  mandatory
    DESCRIPTION
           "The index value used to determine which alerts
        have been added or removed from the alert table.
        This is an incrementing integer starting from zero
        every time the printer is reset.  When the printer
        adds an alert to the table, that alert is assigned
        the next higher integer value from the last item
        entered into the table.  If the index value reaches
        its maximum value, the next item entered will cause
        the index value to roll over and start at zero
        again.  The first event placed in the alert table
        after a reset of the printer shall
        have an index value of 1.  NOTE: The management
        application will read the alert table when a trap
        or event notification occurs or at a periodic rate
        and then parse the table to determine if any new
        entries were added by comparing the last known index
        value with the current highest index value. The
        management application will then update its copy of
        the alert table.  When the printer discovers that
        an alert is no longer active, the printer shall
        remove the row for that alert from the table and
        shall reduce the number of rows in the table.  The
        printer may add or delete any number of rows from
        the table at any time.  The management station
        can detect when binary alerts have been deleted by
        requesting an attribute of each alert, and noting
        alerts as deleted when that retrieval is not possible."
    ::= { prtAlertEntry  1 }

prtAlertSeverityLevel OBJECT-TYPE
    SYNTAX  INTEGER {
    other(1),
    critical(3),
    warning(4)
}
    ACCESS  read-only
    STATUS  mandatory
    DESCRIPTION
           "The level of severity of this alert table entry.  The printer
        determines the severity level assigned to each entry into the
        table."
    ::= { prtAlertEntry  2 }

prtAlertTrainingLevel OBJECT-TYPE
    SYNTAX  INTEGER {
    other(1),
    unknown(2),
    untrained(3),
    trained(4),
    fieldService(5),
    management(6)
}
    ACCESS  read-only
    STATUS  mandatory
    DESCRIPTION
           "The level of training required to handle this alert. The
        training level is an enumeration that is determined and
        assigned by the printer manufacturer based on the information
        or the training required to handle this alert.  The printer
        will break alerts into these different training levels.  It is
        the responsibility of the management application in the system
        to determine how a particular alert is handled and how and to
        whom that alert is routed.  The following are the four
        training levels of alerts:
               Field Service - Alerts that typically require advanced
                      training and technical knowledge of the printer
                      and its sub-units. An example of a technical
                      person would be a manufacture's Field Service
                      representative, or other person formally
                      trained by the manufacturer or similar
                      representative.
               Trained - Alerts that require an intermediate or moderate
                      level of knowledge of the printer and its
                      sub-units. A typical examples of alerts that
                      a trained operator can handle is replacing
                      toner cartridges.
               Untrained - Alerts that can be fixed without prior
                      training either because the action to correct
                      the alert is obvious or the printer can help the
                      untrained person fix the problem. A typical
                      example of such an alert is reloading paper
                      trays and emptying output bins on a low end
                      printer.
               Management - Alerts that have to do with overall
                      operation of and configuration of the printer.
                      Examples of management events are configuration
                      change of sub-units."
    ::= { prtAlertEntry  3 }

prtAlertGroup OBJECT-TYPE
    SYNTAX  INTEGER {
    other(1),
    hostResourcesMIBStorageTable(3),
    hostResourcesMIBDeviceTable(4),
    generalPrinter(5),
    cover(6),
    localization(7),
    input(8),
    output(9),
    marker(10),
    markerSupplies(11),
    markerColorant(12),
    mediaPath(13),
    channel(14),
    interpreter(15),
    consoleDisplayBuffer(16),
    consoleLights(17)
}
    ACCESS  read-only
    STATUS  mandatory
    DESCRIPTION
           "The type of sub-unit within the printer model that this alert
        is related.  Input, output, and markers are examples of
        printer model groups, i.e., examples of types of sub-units.
        Whereever possible, these enumerations match the
        sub-identifier that identifies the relevant table in the
        printmib."
    ::= { prtAlertEntry  4 }

prtAlertGroupIndex OBJECT-TYPE
    SYNTAX  INTEGER (-2147483648..2147483647)
    ACCESS  read-only
    STATUS  mandatory
    DESCRIPTION
           "An index of the row within the principle table in the
        group identified by prtAlertGroup that represents the
        sub-unit of the printer that caused this alert.  The
        combination of the Group and the GroupIndex defines
        exactly which printer sub-unit caused the alert.; for
        example, Input #3, Output #2, and Marker #1.
        Every object in this MIB is indexed with hrDeviceIndex and
        optionally, another index variable.  If this other index
        variable is present in the table that generated the alert, it
        will be used as the value for this object.  Otherwise, this
        value shall be -1."
    ::= { prtAlertEntry  5 }

prtAlertLocation OBJECT-TYPE
    SYNTAX  INTEGER (-2147483648..2147483647)
    ACCESS  read-only
    STATUS  mandatory
    DESCRIPTION
           "The sub-unit location that is defined by the printer
        manufacturer to further refine the location of this alert
        within the designated sub-unit.  The location is used in
        conjunction with the Group and GroupIndex values; for
        example, there is an alert in Input #2 at location number 7."
    ::= { prtAlertEntry  6 }

prtAlertCode OBJECT-TYPE
    SYNTAX  INTEGER {
    other(1),
    unknown(2),
    coverOpen(3),
    coverClosed(4),
    interlockOpen(5),
    interlockClosed(6),
    configurationChange(7),
    jam(8),
    doorOpen(501),
    doorClosed(502),
    powerUp(503),
    powerDown(504),
    inputMediaTrayMissing(801),
    inputMediaSizeChange(802),
    inputMediaWeightChange(803),
    inputMediaTypeChange(804),
    inputMediaColorChange(805),
    inputMediaFormPartsChange(806),
    inputMediaSupplyLow(807),
    inputMediaSupplyEmpty(808),
    outputMediaTrayMissing(901),
    outputMediaTrayAlmostFull(902),
    outputMediaTrayFull(903),
    markerFuserUnderTemperature(1001),
    markerFuserOverTemperature(1002),
    markerTonerEmpty(1101),
    markerInkEmpty(1102),
    markerPrintRibbonEmpty(1103),
    markerTonerAlmostEmpty(1104),
    markerInkAlmostEmpty(1105),
    markerPrintRibbonAlmostEmpty(1106),
    markerWasteTonerReceptacleAlmostFull(1107),
    markerWasteInkReceptacleAlmostFull(1108),
    markerWasteTonerReceptacleFull(1109),
    markerWasteInkReceptacleFull(1110),
    markerOpcLifeAlmostOver(1111),
    markerOpcLifeOver(1112),
    markerDeveloperAlmostEmpty(1113),
    markerDeveloperEmpty(1114),
    mediaPathMediaTrayMissing(1301),
    mediaPathMediaTrayAlmostFull(1302),
    mediaPathMediaTrayFull(1303),
    interpreterMemoryIncrease(1501),
    interpreterMemoryDecrease(1502),
    interpreterCartridgeAdded(1503),
    interpreterCartridgeDeleted(1504),
    interpreterResourceAdded(1505),
    interpreterResourceDeleted(1506),
    interpreterResourceUnavailable(1507)
}
    ACCESS  read-only
    STATUS  mandatory
    DESCRIPTION
           "The code that describes the type of alert for this entry in
        the table.  There are different codes for each
        sub-unit type: for example, Media Supply Low and Media
        Supply Empty are Aler codes for the Input sub-unit."
    ::= { prtAlertEntry  7 }

prtAlertDescription OBJECT-TYPE
    SYNTAX  OCTET STRING
    ACCESS  read-only
    STATUS  mandatory
    DESCRIPTION
           "A description of this alert entry in the localization
        specified by prtGeneralCurrentLocalization.  The description is
        provided by the printer to further elaborate on the enumerated
        alert or provide information in the case where the code is
        classified ask `other' or `unknown'.  The printer is required
        to return a description string but the string may be a null
        string."
    ::= { prtAlertEntry  8 }

printerV1Alert OBJECT IDENTIFIER ::= { prtAlert  2 }

printerV2AlertPrefix OBJECT IDENTIFIER ::= { printerV1Alert  0 }

--printerV2Alert TRAP-TYPE
 --   ENTERPRISE  { printerV2AlertPrefix }
--    VARIABLES   { prtAlertIndex,  prtAlertSeverityLevel,  prtAlertGroup, 
--prtAlertGroupIndex,  prtAlertLocation,  prtAlertCode }
 --   DESCRIPTION
--           "This trap is sent whenever a critical event is added to the
--        prtAlertTable."
--    ::= 1

prtAlertTime OBJECT-TYPE
    SYNTAX  TimeTicks
    ACCESS  read-only
    STATUS  mandatory
    DESCRIPTION
           "The value of sysUpTime at the time that this alert was
        generated."
    ::= { prtAlertEntry  9 }

prtMIBConformance OBJECT IDENTIFIER ::= { printmib  2 }

prtMIBCompliance OBJECT IDENTIFIER ::= { prtMIBConformance  1 }

prtMIBGroups OBJECT IDENTIFIER ::= { prtMIBConformance  2 }

prtGeneralGroup OBJECT IDENTIFIER ::= { prtMIBGroups  1 }

prtResponsiblePartyGroup OBJECT IDENTIFIER ::= { prtMIBGroups  2 }

prtInputGroup OBJECT IDENTIFIER ::= { prtMIBGroups  3 }

prtExtendedInputGroup OBJECT IDENTIFIER ::= { prtMIBGroups  4 }

prtInputMediaGroup OBJECT IDENTIFIER ::= { prtMIBGroups  5 }

prtOutputGroup OBJECT IDENTIFIER ::= { prtMIBGroups  6 }

prtExtendedOutputGroup OBJECT IDENTIFIER ::= { prtMIBGroups  7 }

prtOutputDimensionsGroup OBJECT IDENTIFIER ::= { prtMIBGroups  8 }

prtOutputFeaturesGroup OBJECT IDENTIFIER ::= { prtMIBGroups  9 }

prtMarkerGroup OBJECT IDENTIFIER ::= { prtMIBGroups  10 }

prtMarkerSuppliesGroup OBJECT IDENTIFIER ::= { prtMIBGroups  11 }

prtMarkerColorantGroup OBJECT IDENTIFIER ::= { prtMIBGroups  12 }

prtMediaPathGroup OBJECT IDENTIFIER ::= { prtMIBGroups  13 }

prtChannelGroup OBJECT IDENTIFIER ::= { prtMIBGroups  14 }

prtInterpreterGroup OBJECT IDENTIFIER ::= { prtMIBGroups  15 }

prtConsoleGroup OBJECT IDENTIFIER ::= { prtMIBGroups  16 }

prtAlertTableGroup OBJECT IDENTIFIER ::= { prtMIBGroups  17 }

prtAlertTimeGroup OBJECT IDENTIFIER ::= { prtMIBGroups  18 }

END
